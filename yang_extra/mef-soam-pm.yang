module mef-soam-pm {
  namespace "http://metroethernetforum.org/ns/yang/mef-soam-pm";
  prefix mef-soam-pm;

  import mef-cfm {
    prefix cfm;
    revision-date 2012-04-16;
  }

  import ietf-yang-types {
    prefix yang;
    revision-date 2010-09-24;
  }

  organization "Metro Ethernet Forum";
  contact 
    "Web URL: http://metroethernetforum.org/
         E-mail:  mibs@metroethernetforum.org
         Postal:  Metro Ethernet Forum
                  6033 W. Century Boulevard, Suite 830
                  Los Angeles, CA 90045
                  U.S.A.
         Phone:   +1 310-642-2800
         Fax:     +1 310-642-2808";

  description 
    "This YANG module contains the management data definitions for the
         management of Ethernet Services Operations, Administration and
         Maintenance for Performance Monitoring and extends the Connectivity
         Fault Management (CFM) YANG modules.
         
         Reference Overview:
               A number of base documents have been used to create th
               SOAM PM YANG Module.
               The following are the abbreviations for the baseline documents:
               [802.1q] refers to IEEE 802.1Q-2011 'IEEE Standard for Local and
                   metro-politan area networks --Media Access Control (MAC)
                   Bridges and Virtual Bridged Local Area Networks, August 2011
               [MEF SOAM PM IA] refers to 'Service OAM Performance Monitoring
                   Implementation Agreement', January 2012
               [MEF SOAM PM MIB] refers to 'Service OAM Performance Monitoring
                   Definition of Managed Objects', January 2012
               [Y.1731] refers to ITU-T Y.1731 'OAM functions and mechanisms
                   for Ethernet based networks', July 2011";

  revision 2012-04-16 {
    description
      "Initial revision";
    reference
      "Service OAM Performance Monitoring YANG Module (MEF XX), April 2012";
  }

  //
  // Type definitions related to MEF SOAM PM
  //

  typedef suspect-status-type {
    type boolean;
    description 
      "This boolean data type indicates whether the measurement interval
             has been marked as suspect.
                   
             The object is set to false at the start of a measurement
             interval. It is set to true when there is a discontinuity in the
             performance measurements during the measurement interval.
             Conditions for a discontinuity include, but are not limited to
             the following:
                   
               1 - The local time-of-day clock is adjusted by at least 10
                   seconds
               2 - The conducting of a performance measurement is halted before
                   the current measurement interval is completed
               3 - A local test, failure, or reconfiguration that disrupts
                   service";
    reference
      "[MEF SOAM PM IA] R39, R40, 41 and R42";
  }

  typedef performance-monitoring-interval-type {
    type uint32 {
      range "3..3600000";
    }
    units ms;
    description
      "This integer data type indicates the transmission time between the
       SOAM PM frames for session, in ms.";
  }
  typedef test-pattern-type {
    type enumeration {
      enum null-signal-without-crc-32 {
        description
          "This test pattern is a Null signal without CRC-32.";
      }
      enum null-signal-with-crc-32 {
        description
          "This test pattern is a Null signal with CRC-32.";
      }
      enum prbs-2311-without-crc-32 {
        description "This test pattern is a PRBS 2^31-1 without CRC-32.";
      }
      enum prbs-2311-with-crc-32 {
        description "This test pattern is a PRBS 2^31-1 with CRC-32.";
      }
    }

    description
      "This enumeration data type indicates the type of test pattern to be sent
       in an OAM PDU Data TLV.";
    reference
      "MEF-SOAM-TC-MIB.MefSoamTcTestPatternType";
  }

  typedef session-status-type {
    type enumeration {
      enum active {
        description
          "Indicates the measurement instance is active.";
      }
      enum not-active {
        description
          "Indicates the measurement instance is not active.";
      }
    }

    description
      "This enumeration data type defines the status of PM session of a MEP.";
    reference
      "MEF-SOAM-TC-MIB.MefSoamTcStatusType";
  }

  typedef availability-type {
    type enumeration {
      enum available {
        description
          "Indicates the MEP is available.";
      }
      enum unavailable {
        description
          "Indicates the MEP is unavailable.";
      }
      enum unknown {
        description
          "Indicates the availability is not known, for instance because
           insufficient time has passed to make an availability
           calculation, the time has been excluded because of a
           maintenance interval, or because availability measurement is
           not enabled.";
      }
    }

    description
      "This enumeration data type defines the availability of a session,
       measured by a loss measurement session.";
    reference
      "MEF-SOAM-TC-MIB.MefSoamTcAvailabilityType";
  }

  typedef measurement-bin-type {
    type enumeration {
      enum two-way-frame-delay {
        description
          "Indicates a measurement bin for two-way Frame Delay.";
      }
      enum forward-frame-delay {
        description
          "Indicates a measurement bin for one-way Frame Delay in the forward 
           direction.";
      }
      enum backward-frame-delay {
        description 
          "Indicates a measurement bin for one-way Frame Delay in the backward
           direction.";
      }
      enum two-way-inter-frame-delay-variation {
        description
          "Indicates a measurement bin for two-way Inter-frame Delay
           Variation.";
      }
      enum forward-inter-frame-delay-variation {
        description
          "Indicates a measurement bin for one-way Inter-frame Delay
           Variation in the forward direction.";
      }
      enum backward-inter-frame-delay-variation {
        description
          "Indicates a measurement bin for one-way Inter-frame Delay Variation
           in the backward direction.";
      }
      enum two-way-frame-delay-range {
        description
          "Indicates a measurement bin for two-way Frame Delay Range.";
      }
      enum forward-frame-delay-range {
        description
          "Indicates a measurement bin for one-way Frame Delay Range in the
           forward direction.";
      }
      enum backward-frame-delay-range {
        description
          "Indicates a measurement bin for one-way Frame Delay Range in the
           backward direction.";
      }
    }

    description
      "This enumeration data type indicates whether the bin number is for Frame
       Delay, Inter-Frame Delay Variation or Frame Delay Range.";
    reference
      "MEF-SOAM-TC-MIB.MefSoamTcDelayMeasurementBinType";
  }

  //
  // Groupings related to MEF SOAM PM
  //

  grouping remote-mep-group {
    description
      "This grouping includes objects which identify a remote MEP.";
    choice remote-mep {
      mandatory true;
      description
        "The remote MEP can be identified by either a MAC address or a MEP ID";

      case mac-address {
        leaf mac-address {
          type yang:mac-address;

          description
            "The Target MAC Address Field to be transmitted: A unicast
             destination MAC address.
                         
             This object is only valid for the entity transmitting the
             SOAM Loss and Delay Measurement frames and is ignored by
             the entity receiving SOAM Loss and Delay Measurement
             frames.";
        }
      }
      case mep-id {
        leaf mep-id {
          type string;

          description 
            "The Maintenance Association End Point Identifier of another MEP in
             the same Maintenance Association to which the SOAM Loss or Delay
             Measurement frame is to be sent.
                         
             This object is only valid for the entity transmitting the
             SOAM Loss Measurement or Delay Measurement frames and is
             ignored by the entity receiving SOAM Loss Measurement or
             Delay Measurement frames.";
        }
      }
    }
  }

  grouping measurement-timing-group {
    description
      "This grouping includes objects used for proactive and on-demand
       scheduling of PM measurement sessions.";

    container start-time {
      description
        "This container defines the session start time";

      choice start-time {
        mandatory true;
        description
          "Measurement session start time can be immediate, relative or
           absolute.";

        container immediate {
          presence "Start the measurement session immediately.";

          description
            "This object specifies the start time to be immediately at the time
             of session creation.";
        }
        leaf relative {
          type yang:timeticks;

          description 
            "This object specifies the relative start time, from the current
             system time, to perform on-demand ETH-DM.  This attribute has no
             meaning for proactive ETH-DM.";
        }
        leaf absolute {
          type yang:date-and-time;

          description 
            "This object specifies the scheduled start date/time to perform the
             on-demand Performance Monitoring OAM operations. This attribute
             has no meaning for proactive Performance Monitoring OAM
             operations.";
        }
      }
    }

    container stop-time {
      description
        "This container defines the session stop time";

      choice stop-time {
        mandatory true;
        description
          "Measurement session stop time can be none, relative or
           absolute.";

        container none {
          presence "Never end the measurement session.";

          description
            "This object specifies the measurement  session to never end.";
        }

        leaf relative {
          type yang:timeticks;
          mandatory true;

          description 
            "This object specifies the duration of the Delay Measurement PM
             Session.  The duration time can be specified as forever
             (represented by a zero value) or as relative time (e.g., a
             given number of hours, minutes, and seconds from the start
             time).  If the duration time is relative time, then the
             duration time should be equal to or greater than the frame
             transmission period of the PM function(s) comprising the PM
             Solution";
              
        }

        leaf absolute {
          type yang:date-and-time;

          description 
            "This object specifies the scheduled stop date and time to perform
             on-demand Performance Monitoring OAM operations.  This
             attribute has no meaning for proactive Performance
             Monitoring OAM operations.  The stop date and time value should
             be greater than or equal to the scheduled start date and time
             value.";
        }
      }
    }


    leaf repetition-period {
      type yang:timeticks;
      default 0;

      description 
        "This object specifies a configurable repetition time between
         Measurement Intervals in a Measurement session in hundredths of a
         second.
                 
         If the value is less than or equal to one Measurement Interval
         there is no time gap between the end of one Measurement
         Interval and the start of a new Measurement Interval. This is
         the normal usage case.
                 
         If the value is greater than one Measurement Interval there is
         time gap between the end of one Measurement Interval and the
         start of the next Measurement Interval.";
      reference
        "[MEF SOAM PM IA] R18, D3, R19, R20";
    }
  }

  grouping loss-measurement-configuration-group {
    description
      "This grouping includes configuration objects for the Frame Loss
       Measurement function defined in [Y.1731] and [MEF SOAM PM IA].";
    reference 
      "MEF-SOAM-PM-MIB.mefSoamLmCfgTable, [Y.1731] and [MEF SOAM PM IA]";

    leaf measurement-type {
      type enumeration {
        enum lmm {
          description
            "LMM SOAM PDU generated and received LMR responses tracked.";
        }
        enum slm {
          description
            "SLM SOAM PDU generated and received SLR responses tracked.";
        }
        enum ccm {
          description
            "CCM SOAM PDU generated and received CCM PDUs tracked.";
        }
      }
      default slm;

      description
        "This object specifies what type of Loss Measurement will be
         performed.";
      reference
        "MEF-SOAM-PM-MIB.mefSoamLmCfgType";
    }

    leaf version {
      type enumeration {
        enum Y.1731-2008 {
          description
            "Indicates the PDU formats defined in Y.1731-2008";
        }
        enum Y.1731-2011 {
          description
            "Indicates the PDU formats defined in Y.1731-2011.";
        }
      }
      default Y.1731-2008;

      description 
        "This object indicates the version of the PDUs used to perform Loss
         Measurement.

         The exact PDUs to use are specified by this object in
         combination with measurement-type.";
      reference
        "MEF-SOAM-PM-MIB.mefSoamLmCfgVersion";
    }

    leaf enabled-counters {
      type bits {
        bit forward-transmitted-frames;
        bit forward-received-frames;
        bit forward-min-flr;
        bit forward-max-flr;
        bit forward-average-flr;
        bit backward-transmitted-frames;
        bit backward-received-frames;
        bit backward-min-flr;
        bit backward-max-flr;
        bit backward-average-flr;
        bit soam-pdus-sent;
        bit soam-pdus-received;
        bit availability-forward-high-loss;
        bit availability-forward-consecutive-high-loss;
        bit availability-forward-available;
        bit availability-forward-unavailable;
        bit availabilility-forward-min-flr;
        bit availability-forward-max-flr;
        bit availability-forward-average-flr;
        bit availability-backward-high-loss;
        bit availability-backward-consecutive-high-loss;
        bit availability-backward-available;
        bit available-backward-unavailable;
        bit available-backward-min-flr;
        bit available-backward-max-flr;
        bit available-backward-average-flr;
        bit measured-stats-forward-measured-flr;
        bit measured-stats-backward-measured-flr;
        bit measured-stats-availability-forward-status;
        bit measured-stats-availability-backward-status;
      }
      default " ";

      description 
        "A vector of bits that indicates the type of SOAM LM counters found in
         the current-stats and history-stats that are enabled.
                 
         A present bit enables the specific SOAM LM counter. A not present
         bit disables the SOAM LM counter.
                 
         If a particular SOAM LM counter is not supported the BIT value
         is not present.
                 
         Not all SOAM LM counters are supported for all SOAM LM types. ";
      reference
        "MEF-SOAM-PM-MIB.mefSoamLmCfgMeasurementEnable";
    }

    leaf message-period {
      type performance-monitoring-interval-type;
      units ms;
      default 1000;

      description
        "This object specifies the interval between Loss Measurement OAM message
         transmission. For Loss Measurement monitoring applications the
         default value is 1 sec.
                 
         This object is not applicable if measurement-type is set to
         'ccm' and is ignored for that Loss Measurement Type.";
      reference
        "MEF-SOAM-PM-MIB.mefSoamLmCfgMessagePeriod";
    }

    leaf priority {
      type cfm:priority-type;
      mandatory true;

      description 
        "This object specifies the priority of frames with Performance
         Monitoring OAM message information.";
      reference
        "MEF-SOAM-PM-MIB.mefSoamLmCfgPriority";
    }

    leaf frame-size {
      type uint32 {
        range "64 .. 9600";
      }
      units bytes;
      default 64;

      description 
        "This object specifies the Loss Measurement frame size between 64 bytes
         and the maximum transmission unit of the EVC.
                 
         The range of frame sizes from 64 through 2000 octets need to be
         supported, and the range of frame sizes from 2001 through 9600
         octets is suggested be supported.
                 
        The adjustment to the frame size of the standard frame size is
        accomplished by the addition of a Data or Test TLV. A Data or
        Test TLV is only added to the frame if the frame size is greater
        than 64 bytes.";
      reference
        "MEF-SOAM-PM-MIB.mefSoamLmCfgFrameSize";
    }

    leaf data-pattern {
      type enumeration {
        enum zeroes {
          description
            "Indicates the Data TLV contains all zeros.";
        }
        enum ones {
          description
            "Indicates the Data TLV contains all ones.";
        }
      }
      default zeroes;

      description 
        "This object specifies the LM data pattern included in a Data TLV when
         the size of the LM frame is determined by the frame-size object
         and test-tlv-included is 'false'.
                 
         If the frame size object does not define the LM frame size or
         test-tlv-included is 'true' the value of this object is ignored.";
      reference
        "MEF-SOAM-PM-MIB.mefSoamLmCfgDataPattern";
    }

    leaf test-tlv-included {
      type boolean;
      default false;

      description 
        "This object indicates whether a Test TLV or Data TLV is included when
         the size of the LM frame is determined by the
         frame-size object.
                 
         A value of 'true' indicates that the Test TLV is to be
         included. A value of 'false' indicates that the Data TLV is to
         be included.
                 
         If the frame-size object does not define the LM frame size the
         value of this object is ignored.";
      reference
        "MEF-SOAM-PM-MIB.mefSoamLmCfgTestTlvIncluded";
    }

    leaf test-tlv-pattern {
      type test-pattern-type;
      default null-signal-without-crc-32;

      description 
        "This object specifies the type of test pattern to be sent in the LM
         frame Test TLV when the size of LM PDU is determined by the
         frame-size object and test-tlv-included is 'true'. If the frame
         size object does not define the LM frame size or
         test-tlv-included is 'false' the value of this object is
         ignored.";
      reference
        "MEF-SOAM-PM-MIB.mefSoamLmCfgTestTlvPattern";
    }

    leaf measurement-interval {
      type uint32 {
        range "1..525600";
      }
      units minutes;
      default 15;

      description 
        "This object specifies the Measurement Interval for FLR statistics, in
         minutes.
                 
         A Measurement Interval of 15 minutes needs to be supported,
         other intervals may be supported.";
      reference
        "MEF-SOAM-PM-MIB.mefSoamLmCfgMeasurementInterval";
    }

    leaf number-intervals-stored {
      type uint32 {
        range "2..1000";
      }
      default 32;
      description 
        "This object specifies the number of completed measurement intervals to
         store in the history statistic table.
                 
         At least 32 completed measurement intervals are to be
         stored. 96 measurement intervals are recommended to be stored.";
      reference
        "MEF-SOAM-PM-MIB.mefSoamLmCfgNumIntervalsStored";
    }

    leaf align-measurement-intervals {
      type boolean;
      default true;

      description 
        "This object specifies whether the measurement intervals for the Loss
         Measurement session are aligned with a zero offset to real
         time.
                 
         The value 'true' indicates that each Measurement Interval
         starts at a time which is aligned to NE time source hour if the
         interval is a factor of an hour, i.e. 60min/15min = 4. For
         instance, a measurement time interval of 15 minutes would
         stop/start the measurement interval at 0, 15, 30, and 45
         minutes of an hour. A measurement interval of 7 minutes would
         not align to the hour since 7 minutes is NOT a factor of an
         hour, i.e.  60min/7min = 8.6, and the behavior is the same as
         if the object is set to 'false'.
                 
         The value 'false' indicates that each Measurement Interval
         starts at a time which is indicated by repetition-period.
                 
         One side effect of the usage of this parameter is that if the
         value is true and the repetition-period is not a factor of an
         hour then the start of the next Measurement Interval will be
         delayed until the next factor of an hour.";
      reference
        "MEF-SOAM-PM-MIB.mefSoamLmCfgAlignMeasurementIntervals";
    }

    leaf align-measurement-offset {
      type uint32 {
        range "0..525600";
      }
      units minutes;
      default 0;

      description 
        "This object specifies the offset in minutes from the time of day value
         if align-measurement-intervals is 'true' and the repetition
         time is a factor of 60 minutes. If not, the value of this
         object is ignored.
                 
         If the Measurement Interval is 15 minutes and
         align-measurement-intervals is true and if this object was set
         to 5 minutes, the Measurement Intervals would start at 5, 20,
         35, 50 minutes past each hour.";
      reference
        "MEF-SOAM-PM-MIB.mefSoamLmCfgAlignMeasurementOffset";
    }

    leaf availability-measurement-interval {
      type uint32 {
        range "1..525600";
      }
      units minutes;
      default 15;

      description 
        "This object specifies the availability measurement interval in minutes.
                         
         A measurement interval of 15 minutes is to be supported, other
         intervals can be supported.";
      reference
        "MEF-SOAM-PM-MIB.mefSoamLmCfgAvailabilityMeasurementInterval";
    }
    leaf availability-number-consecutive-flr-measurements {
      type uint32 {
        range "1..1000000";
      }
      default 10;

      description 
        "This object specifies a configurable number of consecutive loss
         measurement PDUs to be used in evaluating the
         availability/unavailability status of each availability
         indicator per MEF 10.2.1.  Loss Measurement PDUs (LMMs, CCMs or
         SLMs) are sent regularly with a period defined by
         message-period.  Therefore, this object, when multiplied by
         message-period, is equivalent to the Availability parameter of
         'delta_t' as specified by MEF 10.2.1.
                 
         If the measurement-type is lmm or ccm, this object defines the
         number of LMM or CCM PDUs transmitted during each 'delta_t'
         period.  The Availability flr for a given 'delta_t' can be
         calculated based on the counters in the last LMM/R or CCM
         during this 'delta_t' and the last LMM/R or CCM in the previous
         'delta_t'.
                 
          If the measurement-type is slm, this object defines the number
          of SLM PDUs transmitted during each 'delta_t' period.  The
          Availability flr for a given 'delta_t' is calculated based on
          the number of those SLM PDUs that are lost.
                 
          If the measurement-type is lmm or ccm, the number range of 1
          through 10 must be supported. The number range of 10 through
          1000000 may be supported, but is not mandatory.
                 
          If the measurement-type is slm, the number range of 10 through
          100 must be supported. The number range of 100 through 1000000
          may be supported, but is not mandatory.";
      reference
        "MEF-SOAM-PM-MIB.mefSoamLmCfgAvailabilityNumConsecutiveMeasPdus";
    }
    leaf availability-flr-threshold {
      type uint32 {
        range "0..100000";
      }
      units milli-percent;
      default 50000;

      description 
        "This object specifies a configurable availability threshold to be used
         in evaluating the availability/unavailability status of an
         availability indicator per MEF 10.2.1. The availability
         threshold range of 0.00 (0) through 1.00 (100000) is
         supported. This parameter is equivalent to the Availability
         parameter of 'C' as specified by MEF 10.2.1.
                         
         Units are in milli-percent, where 1 indicates 0.001 percent.";
      reference
        "MEF-SOAM-PM-MIB.mefSoamLmCfgAvailabilityFlrThreshold";
    }

    leaf availability-number-consecutive-intervals {
      type uint32 {
        range "1..1000";
      }
      default 10;

      description 
        "This object specifies a configurable number of consecutive availability
         indicators to be used to determine a change in the availability
         status as indicated by MEF 10.2.1. This parameter is equivalent
         to the Availability parameter of 'n' as specified by MEF
         10.2.1.
                 
         The number range of 1 through 10 must be supported. The number
         range of 1 through 1000 may be supported, but is not mandatory.";
      reference
        "MEF-SOAM-PM-MIB.mefSoamLmCfgAvailabilityNumConsecutiveIntervals";
    }

    leaf availability-number-consecutive-high-flr {
      type uint32 {
        range "1..1000";
      }
      default 5;

      description 
        "This object specifies a configurable number of consecutive availability
         indicators to be used for assessing CHLI.  This parameter is
         equivalent to the Resilency parameter of 'p' as specified by
         MEF 10.2.1.
                 
         Availability-consecutive-high-flr must be strictly less than
         availability-number-consecutive-intervals. If not, the count of
         high loss intervals over time, and the count of consecutive
         high loss levels, is disabled.
                 
         The number range of 1 through 10 must be supported. The number
         range of 1 through 1000 may be supported, but is not mandatory.";
      reference
        "MEF-SOAM-PM-MIB.mefSoamLmCfgAvailabilityNumConsecutiveHighFlr";
    }

    leaf session-type {
      type enumeration {
        enum proactive {
          description
            "The current session is 'proactive'";
        }
        enum on-demand {
          description
            "The current session is 'on-demand'";
        }
      }

      description
        "This object indicates whether the current session is defined to be
         'proactive' or 'on-demand'.";
      reference
        "[MEF SOAM IA] R3";
    }

    list thresholds {
      key id;
      description 
        "This list contains the list of Loss Measurement configuration threshold
         values for LM Performance Monitoring.
                 
         The main purpose of the threshold configuration list is to
         configure threshold alarm notifications indicating that a
         specific performance metric is not being met.";

      leaf id {
        type uint32;
        description 
          "The index of the threshold number for the specific LM threshold
           entry.

           An index value of '1' needs to be supported. Other index
           values can also be supported.";
      }

      leaf enabled-thresholds {
        type bits {
          bit measured-flr-forward;
          bit max-flr-forward;
          bit average-flr-forward;
          bit measured-flr-backward;
          bit max-flr-backward;
          bit average-flr-backward;
          bit forward-high-loss;
          bit forward-consecutive-high-loss;
          bit backward-high-loss;
          bit backward-consecutive-high-loss;
          bit forward-unavailable-count;
          bit forward-available-ratio;
          bit backward-unavailable-count;
          bit backward-available-ratio;
        }
        default " ";
        description 
          "A vector of bits that indicates the type of SOAM LM thresholds
           notifications that are enabled.
                     
           A present but enables the specific SOAM LM threshold
           notifica-tion and when the specific counter is enabled and
           the threshold is crossed a notification is generated.
                     
           A not present bit disables the specific SOAM LM threshold
           notification.
                     
           If a particular SOAM LM threshold is not supported the BIT
           value is not present.";
      }

      leaf measured-flr-forward {
        type uint32 {
          range "0..100000";
        }
        units milli-percent;
        default 100000;

        description 
          "This object is used to set the measured forward frame loss ratio
           threshold value that will be used to determine if a threshold
           notification is generated.";
        reference
          "MEF-SOAM-PM-MIB.mefSoamLmThresholdCfgMeasuredFlrForwardThreshold";
      }

      leaf max-flr-forward {
        type uint32 {
          range "0..100000";
        }
        units milli-percent;
        default 100000;

        description 
          "This object is used to set the maximum forward frame loss ratio
           threshold value that will be used to determine if a threshold
           notification is generated.";
        reference
          "MEF-SOAM-PM-MIB.mefSoamLmThresholdCfgMaxFlrForwardThreshold";
      }

      leaf average-flr-forward {
        type uint32 {
          range "0..100000";
        }
        units milli-percent;
        default 100000;

        description 
          "This object is used to set the average forward frame loss ratio
           threshold value that will be used to determine if a threshold
           notification is generated.";
        reference
          "MEF-SOAM-PM-MIB.mefSoamLmThresholdCfgAvgFlrForwardThreshold";
      }

      leaf measured-flr-backward {
        type uint32 {
          range "0..100000";
        }
        units milli-percent;
        default 100000;

        description 
          "This object is used to set the measured backward frame loss ratio
           threshold value that will be used to determine if a threshold
           notification is generated.";
        reference
          "MEF-SOAM-PM-MIB.mefSoamLmThresholdCfgMeasuredFlrBackwardThreshold";
      }

      leaf max-flr-backward {
        type uint32 {
          range "0..100000";
        }
        units milli-percent;
        default 100000;

        description 
          "This object is used to set the maximum backward frame loss ratio
           threshold value that will be used to determine if a threshold
           notification is generated.";
        reference
          "MEF-SOAM-PM-MIB.mefSoamLmThresholdCfgMaxFlrBackwardThreshold";
      }
      leaf average-flr-backward {
        type uint32 {
          range "0..100000";
        }
        units milli-percent;
        default 100000;

        description 
          "This object is used to set the average backward frame loss ratio
           threshold value that will be used to determine if a threshold
           notification is generated.";
        reference
          "MEF-SOAM-PM-MIB.mefSoamLmThresholdCfgAvgFlrBackwardThreshold";
      }

      leaf forward-high-loss {
        type uint32;
        default 2147483647;

        description 
          "This object is used to set the forward high loss threshold value that
           will be used to determine if a threshold notification is
           generated.";
        reference
          "MEF-SOAM-PM-MIB.mefSoamLmThresholdCfgForwardHighLossThreshold";
      }
      leaf forward-consecutive-high-loss {
        type uint32;
        default 2147483647;

        description 
          "This object is used to set the consecutive forward high loss
           threshold value that will be used to determine if a threshold
           notification is generated.";
        reference
          "MEF-SOAM-PM-MIB." +
          "mefSoamLmThresholdCfgForwardConsecutiveHighLossThreshold";
      }
      leaf backward-high-loss {
        type uint32;
        default 2147483647;

        description 
          "This object is used to set the backward high loss threshold value
           that will be used to determine if a threshold notification is 
           generated.";
        reference
          "MEF-SOAM-PM-MIB.mefSoamLmThresholdCfgBackwardHighLossThreshold";
      }
      leaf backward-consecutive-high-loss {
        type uint32;
        default 2147483647;

        description 
          "This object is used to set the consecutive backward high loss 
           threshold value that will be used to determine if a threshold
           notification is generated.";
        reference
          "MEF-SOAM-PM-MIB." +
          "mefSoamLmThresholdCfgBackwardConsecutiveHighLossThreshold";
      }

      leaf forward-unavailable-count {
        type uint32;
        default 2147483647;

        description 
          "This object is used to set the forward unavailability threshold value
           that will be used to determine if a threshold notification is
           generated.";
        reference
          "MEF-SOAM-PM-MIB.mefSoamLmThresholdCfgForwardUnavailCountThreshold";
      }

      leaf forward-available-ratio {
        type uint32 {
          range "0..100000";
        }
        units milli-percent;
        default 0;

        description 
          "This object is used to set the forward availability/total time ratio
           threshold value that will be used to determine if a
           thresh-old notification is generated if the ratio drops below
           the configured value.
                     
           The ratio value is expressed as a percent with a value of 0
           (ra-tio 0.00) through 100000 (ratio 1.00)
                     
           Units are in milli-percent, where 1 indicates 0.001 percent.";
        reference
          "MEF-SOAM-PM-MIB.mefSoamLmThresholdCfgForwardAvailRatioThreshold";
      }

      leaf backward-unavailable-count {
        type uint32;
        default 2147483647;
        description 
          "This object is used to set the backward unavailability threshold
           value that will be used to determine if a threshold notification is
           generated.";
        reference
          "MEF-SOAM-PM-MIB.mefSoamLmThresholdCfgBackwardUnavailCountThreshold";
      }

      leaf backward-available-ratio {
        type uint32 {
          range "0..100000";
        }
        units milli-percent;
        default 0;

        description 
          "This object is used to set the backward availability/total time ratio
           threshold value that will be used to determine if a
           thresh-old notification is generated if the ratio drops below
           the configured value.
                     
           The ratio value is expressed as a percent with a value of 0
           (ratio 0.00) through 100000 (ratio 1.00)
                     
           Units are in milli-percent, where 1 indicates 0.001 percent.";
        reference
          "MEF-SOAM-PM-MIB.mefSoamLmThresholdCfgBackwardAvailRatioThreshold";
      }
    }
  }

  grouping loss-availability-stats-group {
    description
      "This grouping includes availability statistics objects for a SOAM Loss
       Measurement session.";

    leaf suspect-status {
      type suspect-status-type;
      description 
        "This object indicates whether the Measurement Interval has been marked
         as suspect.
                 
         The object is set to false at the start of a measurement
         interval. It is set to true when there is a discontinuity in
         the performance measurements during the Measurement Interval.
         Conditions for a discontinuity include, but are not limited to
         the following:
                 
          1 - The local time-of-day clock is adjusted by at least 10 seconds
          2 - The conducting of a performance measurement is halted before the
              current Measurement Interval is completed
          3 - A local test, failure, or reconfiguration that disrupts service";
    }

    leaf forward-high-loss {
      type yang:gauge32;

      description 
        "This object is the number of high loss intervals (HLI) over time in the
         forward direction.
                 
         The value starts at 0 and increments for every HLI that occurs.
         This parameter is equivalent to 'L Sub T' found in MEF 10.2.1.";
      reference
        "MEF-SOAM-PM-MIB.mefSoamLmCurrentAvailStatsForwardHighLoss";
    }

    leaf backward-high-loss {
      type yang:gauge32;

      description 
        "This object is the number of high loss intervals (HLI) over time in the
         backward direction.
                 
         The value starts at 0 and increments for every HLI that occurs.
         This parameter is equivalent to 'L Sub T' found in MEF 10.2.1.";
      reference
        "MEF-SOAM-PM-MIB.mefSoamLmCurrentAvailStatsBackwardHighLoss";
    }

    leaf forward-consecutive-high-loss {
      type yang:gauge32;

      description 
        "This object is the number of consecutive high loss intervals (CHLI)
        over time in the forward direction.
                 
        The value starts at 0 and increments for every HLI that occurs.
        This parameter is equivalent to 'B Sub T' found in MEF 10.2.1.";
      reference
        "MEF-SOAM-PM-MIB.mefSoamLmCurrentAvailStatsForwardConsecutiveHighLoss";
    }

    leaf backward-consecutive-high-loss {
      type yang:gauge32;

      description 
        "This object is the number of consecutive high loss intervals (CHLI)
         over time in the backward direction.
                 
         The value starts at 0 and increments for every HLI that occurs.
         This parameter is equivalent to 'B Sub T' found in MEF 10.2.1.";
      reference
        "MEF-SOAM-PM-MIB.mefSoamLmCurrentAvailStatsBackwardConsecutiveHighLoss";
    }

    leaf forward-available {
      type yang:gauge32;

      description 
        "This object contains the number of availability indicators during a
        small time interval evaluated as available (low frame loss) in
        the forward direction by this MEP during this measurement
        interval.";
      reference
        "MEF-SOAM-PM-MIB.mefSoamLmCurrentAvailStatsForwardAvailable";
    }

    leaf backward-available {
      type yang:gauge32;

      description 
        "This object contains the number of availability indicators during a
         small time interval evaluated as available (low frame loss) in
         the backward direction by this MEP during this measurement
         interval.";
      reference
        "MEF-SOAM-PM-MIB.mefSoamLmCurrentAvailStatsBackwardAvailable";
    }
    leaf forward-unavailable {
      type yang:gauge32;

      description 
        "This object contains the number of availability indicators during a
         small time interval evaluated as unavailable (high frame loss)
         in the forward direction by this MEP during this measurement
         interval.";
      reference
        "MEF-SOAM-PM-MIB.mefSoamLmCurrentAvailStatsForwardUnavailable";
    }
    leaf backward-unavailable {
      type yang:gauge32;

      description 
        "This object contains the number of availability indicators during a
         small time interval evaluated as unavailable (high frame loss)
         in the backward direction by this MEP during this measurement
         interval.";
      reference
        "MEF-SOAM-PM-MIB.mefSoamLmCurrentAvailStatsBackwardUnavailable";
    }

    leaf forward-min-frame-loss-ratio {
      type uint32 {
        range "0..100000";
      }
      units milli-percent;

      description 
        "This object contains the minimum one-way availability flr in the
         forward direction, from among the set of availability flr values
         calculated by the MEP in this Measurement Interval.  There is
         one availability flr value for each 'delta_t' time period
         within the Measurement Interval, as specified in MEF 10.2.1.
                 
         The flr value is a ratio that is expressed as a percent with a
         value of 0 (ratio 0.00) through 100000 (ratio 1.00).
                 
        Units are in milli-percent, where 1 indicates 0.001 percent.";
      reference
        "MEF-SOAM-PM-MIB.mefSoamLmCurrentAvailStatsForwardMinFlr";
    }

    leaf forward-max-frame-loss-ratio {
      type uint32 {
        range "0..100000";
      }
      units milli-percent;

      description 
        "This object contains the maximum one-way availability flr in the
         forward direction, from among the set of availability flr
         values calculated by the MEP in this Measurement Interval.
         There is one availability flr value for each 'delta_t' time
         period within the Measurement Interval, as specified in MEF
         10.2.1.
                 
         The flr value is a ratio that is expressed as a percent with a
         value of 0 (ratio 0.00) through 100000 (ratio 1.00).
                 
         Units are in milli-percent, where 1 indicates 0.001 percent.";
      reference
        "MEF-SOAM-PM-MIB.mefSoamLmCurrentAvailStatsForwardMaxFlr";
    }

    leaf forward-average-frame-loss-ratio {
      type uint32 {
        range "0..100000";
      }
      units milli-percent;

      description 
        "This object contains the average one-way availability flr in the
         for-ward direction, from among the set of availability flr
         values calculated by the MEP in this Measurement Interval.
         There is one availability flr value for each 'delta_t' time
         period within the Measurement Interval, as specified in MEF
         10.2.1.
                 
         The flr value is a ratio that is expressed as a percent with a
         value of 0 (ratio 0.00) through 100000 (ratio 1.00).
                 
         Units are in milli-percent, where 1 indicates 0.001 percent.";
      reference
        "MEF-SOAM-PM-MIB.mefSoamLmCurrentAvailStatsForwardAvgFlr";
    }

    leaf backward-min-frame-loss-ratio {
      type uint32 {
        range "0..100000";
      }
      units milli-percent;

      description 
        "This object contains the minimum one-way availability flr in the
         backward direction, from among the set of availability flr
         values calculated by the MEP in this Measurement Interval.
         There is one availability flr value for each 'delta_t' time
         period within the Measurement Interval, as specified in MEF
         10.2.1.
                 
        The flr value is a ratio that is expressed as a percent with a
        value of 0 (ratio 0.00) through 100000 (ratio 1.00).
                 
        Units are in milli-percent, where 1 indicates 0.001 percent.";
      reference
        "MEF-SOAM-PM-MIB.mefSoamLmCurrentAvailStatsBackwardMinFlr";
    }

    leaf backward-max-frame-loss-ratio {
      type uint32 {
        range "0..100000";
      }
      units milli-percent;

      description 
        "This object contains the maximum one-way availability flr in the
         backward direction, from among the set of availability flr
         values calculated by the MEP in this Measurement Interval.
         There is one availability flr value for each 'delta_t' time
         period within the Measurement Interval, as specified in MEF
         10.2.1.
                 
         The flr value is a ratio that is expressed as a percent with a
         value of 0 (ratio 0.00) through 100000 (ratio 1.00).
                 
         Units are in milli-percent, where 1 indicates 0.001 percent.";
      reference
        "MEF-SOAM-PM-MIB.mefSoamLmCurrentAvailStatsBackwardMaxFlr";
    }

    leaf backward-average-frame-loss-ratio {
      type uint32 {
        range "0..100000";
      }
      units milli-percent;

      description 
        "This object contains the average one-way availability flr in the
         backward direction, from among the set of availability flr
         values calculated by the MEP in this Measurement Interval.
         There is one availability flr value for each 'delta_t' time
         period within the Measurement Interval, as specified in MEF
         10.2.1.
                 
         The flr value is a ratio that is expressed as a percent with a
         value of 0 (ratio 0.00) through 100000 (ratio 1.00).
                 
         Units are in milli-percent, where 1 indicates 0.001 percent.";
      reference
        "MEF-SOAM-PM-MIB.mefSoamLmCurrentAvailStatsBackwardAvgFlr";
    }
  }

  grouping loss-measurement-stats-group {
    description
      "This grouping includes statistics objects for a SOAM Loss Measurement
       session.";

    leaf suspect-status {
      type suspect-status-type;

      description 
        "Whether the Measurement Interval has been marked as suspect.
                 
         The object is set to false at the start of a measurement
         interval. It is set to true when there is a discontinuity in
         the performance measurements during the Measurement Interval.
         Conditions for a discontinuity include, but are not limited to
         the following:
                 
          1 - The local time-of-day clock is adjusted by at least 10 seconds
          2 - The conducting of a performance measurement is halted before the
              current Measurement Interval is completed
          3 - A local test, failure, or reconfiguration that disrupts service";
      reference
        "MEF-SOAM-PM-MIB.mefSoamLmCurrentStatsSuspect";
    }

    leaf forward-transmitted-frames {
      type yang:gauge32;
      mandatory true;

      description 
        "This object contains the number of frames transmitted in the forward
         direction by this MEP.
                 
         For a PM Session of types lmm or ccm this includes Ethernet
         Service Frames and SOAM PDUs that are in a higher MEG level
         only.
                 
         For a PM Session of type slm this includes the count of SOAM
         ETH-SLM frames only.";
      reference
        "MEF-SOAM-PM-MIB.mefSoamLmCurrentStatsForwardTransmittedFrames";
    }

    leaf forward-received-frames {
      type yang:gauge32;
      mandatory true;

      description 
        "This object contains the number of frames received in the forward
         direction by this MEP.
                 
         For a PM Session of types lmm or ccm this includes Ethernet
         Service Frames and SOAM PDUs that are in a higher MEG level only.
                 
         For a PM Session of type slm this includes the count of SOAM
         ETH-SLM frames only.";
      reference
        "MEF-SOAM-PM-MIB.mefSoamLmCurrentStatsForwardReceivedFrames";
    }

    leaf forward-min-frame-loss-ratio {
      type uint32 {
        range "0..100000";
      }
      units milli-percent;

      description 
        "This object contains the minimum one-way frame loss ratio in the
         forward direction calculated by this MEP for this Measurement
         Interval. The FLR value is a ratio that is expressed as a
         percent with a value of 0 (ratio 0.00) through 100000 (ratio
         1.00).
                 
         Units are in milli-percent, where 1 indicates 0.001 percent.";
      reference
        "MEF-SOAM-PM-MIB.mefSoamLmCurrentStatsForwardMinFlr";
    }

    leaf forward-max-frame-loss-ratio {
      type uint32 {
        range "0..100000";
      }
      units milli-percent;

      description 
        "This object contains the maximum one-way frame loss ratio in the
         forward direction calculated by this MEP for this Measurement
         Interval. The FLR value is a ratio that is expressed as a
         percent with a value of 0 (ratio 0.00) through 100000 (ratio
         1.00).
                 
         Units are in milli-percent, where 1 indicates 0.001 percent.";
      reference
        "MEF-SOAM-PM-MIB.mefSoamLmCurrentStatsForwardMaxFlr";
    }

    leaf forward-average-frame-loss-ratio {
      type uint32 {
        range "0..100000";
      }
      units milli-percent;

      description 
        "This object contains the average one-way frame loss ratio in the
         forward direction calculated by this MEP for this Measurement
         Interval. The FLR value is a ratio that is expressed as a
         percent with a value of 0 (ratio 0.00) through 100000 (ratio
         1.00).
                 
         Units are in milli-percent, where 1 indicates 0.001 percent.";
      reference
        "MEF-SOAM-PM-MIB.mefSoamLmCurrentStatsForwardAvgFlr";
    }

    leaf backward-transmitted-frames {
      type yang:gauge32;
      mandatory true;

      description 
        "This object contains the number of frames transmitted in the backward
         direction by this MEP.
                 
         For a PM Session of type lmm or ccm this includes Ethernet
         Service Frames and SOAM PDUs that are in a higher MEG level
         only.
                 
         For a PM Session of type slm this includes the count of SOAM
         ETH-SLM frames only.";
      reference
        "MEF-SOAM-PM-MIB.mefSoamLmCurrentStatsBackwardTransmittedFrames";
    }

    leaf backward-received-frames {
      type yang:gauge32;
      mandatory true;

      description 
        "This object contains the number of frames received in the backward
         direction by this MEP.
                 
         For a PM Session of type lmm this includes Ethernet Service
         Frames and SOAM PDUs that are in a higher MEG level only.
                 
         For a PM Session of type slm this includes the count of SOAM
         ETH-SLM frames only.";
      reference
        "MEF-SOAM-PM-MIB.mefSoamLmCurrentStatsBackwardReceivedFrames";
    }

    leaf backward-min-frame-loss-ratio {
      type uint32 {
        range "0..100000";
      }
      units milli-percent;

      description 
        "This object contains the minimum one-way frame loss ratio in the
         backward direction calculated by this MEP for this Measurement
         Interval. The FLR value is a ratio that is expressed as a
         percent with a value of 0 (ratio 0.00) through 100000 (ratio
         1.00).
                 
         Units are in milli-percent, where 1 indicates 0.001 percent.";
      reference
        "MEF-SOAM-PM-MIB.mefSoamLmCurrentStatsBackwardMinFlr";
    }

    leaf backward-max-frame-loss-ratio {
      type uint32 {
        range "0..100000";
      }
      units milli-percent;

      description 
        "This object contains the maximum one-way frame loss ratio in the
         backward direction calculated by this MEP for this Measurement
         Interval. The FLR value is a ratio that is expressed as a
         percent with a value of 0 (ratio 0.00) through 100000 (ratio
         1.00).
                 
         Units are in milli-percent, where 1 indicates 0.001 percent.";
      reference
        "MEF-SOAM-PM-MIB.mefSoamLmCurrentStatsBackwardMaxFlr";
    }

    leaf backward-average-frame-loss-ratio {
      type uint32 {
        range "0..100000";
      }
      units milli-percent;

      description 
        "This object contains the average one-way frame loss ratio in the
         backward direction calculated by this MEP for this Measurement
         Interval. The FLR value is a ratio that is expressed as a
         percent with a value of 0 (ratio 0.00) through 100000 (ratio
         1.00).

         Units are in milli-percent, where 1 indicates 0.001 percent.";
      reference
        "MEF-SOAM-PM-MIB.mefSoamLmCurrentStatsBackwardAvgFlr";
    }

    leaf soam-pdus-sent {
      type yang:gauge32;
      description 
        "This object contains the count of the number of SOAM PDUs sent during
         this Measurement Interval.
                 
         This object applies when type is lmm, slm or ccm. It indicates
         the number of LMM, CCM, or SLM SOAM frames transmitted.";
      reference
        "MEF-SOAM-PM-MIB.mefSoamLmCurrentStatsSoamPdusSent";
    }

    leaf soam-pdus-received {
      type yang:gauge32;

      description 
        "This object contains the count of the number of SOAM PDUs PDUs received
         in this Measurement Interval.
                 
         This object applies when type is lmm, slm, or ccm. This object
         indicates the number of LMR, CCM, or SLR SOAM frames received.";
      reference
        "MEF-SOAM-PM-MIB.mefSoamLmCurrentStatsSoamPdusReceived";
    }
  }

  grouping delay-measurement-configuration-group {
    description
      "This grouping includes configuration objects for the Delay Measurement
       function defined in [Y.1731] and [MEF SOAM PM IA].";
    reference 
      "MEF-SOAM-PM-MIB.mefSoamDmCfgTable, [Y.1731], and [MEF SOAM PM IA].";

    leaf measurement-type {
      type enumeration {
        enum dmm {
          description
            "DMM SOAM PDU generated, DMR responses received (one-way or two-way
             measurements).";
        }
        enum dm1-transmitted {
          description
            "1DM SOAM PDU generated (one-way measurements are made by the
             receiver).";
        }
        enum dm1-received {
          description
            "1DM SOAM PDU received and tracked (one-way measurements).";
        }
      }
      mandatory true;

      description 
        "This object indicates what type of Delay Measurement is to be
         performed.
                 
         The exact PDUs to use are specified by this object in
         combination with version.";
    }

    leaf version {
      type enumeration {
        enum Y.1731-2008 {
          description
            "Indicates the PDU formats defined in Y.1731-2008.";
        }
        enum Y.1731-2011 {
          description
            "Indicates the PDU formats defined in Y.1731-2011.";
        }
      }
      default Y.1731-2008;

      description 
        "This object indicates the version of the PDUs used to perform Delay
         Measurement.
                 
         The exact PDUs to use are specified by this object in
         combination with measurement-type.";
      reference
        "[Y.1731]";
    }

    leaf measurement-enable {
      type bits {
        bit soam-pdus-sent;
        bit soam-pdus-received;
        bit frame-delay-two-way-bins;
        bit frame-delay-two-way-min;
        bit frame-delay-two-way-max;
        bit frame-delay-two-way-average;
        bit frame-delay-forward-bins;
        bit frame-delay-forward-min;
        bit frame-delay-forward-max;
        bit frame-delay-forward-average;
        bit frame-delay-backward-bins;
        bit frame-delay-backward-min;
        bit frame-delay-backward-max;
        bit frame-delay-backward-average;
        bit inter-frame-delay-variation-forward-bins;
        bit inter-frame-delay-variation-forward-min;
        bit inter-frame-delay-variation-forward-max;
        bit inter-frame-delay-variation-forward-average;
        bit inter-frame-delay-variation-backward-bins;
        bit inter-frame-delay-variation-backward-min;
        bit inter-frame-delay-variation-backward-max;
        bit inter-frame-delay-variation-backward-average;
        bit inter-frame-delay-variation-two-way-bins;
        bit inter-frame-delay-variation-two-way-min;
        bit inter-frame-delay-variation-two-way-max;
        bit inter-frame-delay-variation-two-way-average;
        bit frame-delay-range-forward-bins;
        bit frame-delay-range-forward-max;
        bit frame-delay-range-forward-average;
        bit frame-delay-range-backward-bins;
        bit frame-delay-range-backward-max;
        bit frame-delay-range-backward-average;
        bit frame-delay-range-two-way-bins;
        bit frame-delay-range-two-way-max;
        bit frame-delay-range-two-way-average;
        bit measured-stats-frame-delay-two-way;
        bit measured-stats-frame-delay-forward;
        bit measured-stats-frame-delay-backward;
        bit measured-stats-inter-frame-delay-variation-two-way;
        bit measured-stats-inter-frame-delay-variation-forward;
        bit measured-stats-inter-frame-delay-variation-backward;
      }
      default " ";

      description 
        "A vector of bits that indicates the type of SOAM DM counters that
                 are enabled.
                 
                 A present bit enables the specific SOAM DM counter.
                 
                 A not present bit disables the SOAM DM counter.
                 
                 If a particular SOAM DM counter is not supported the BIT value
                 is not present.
                 
                 Not all SOAM DM counters are supported for all SOAM DM types.";
    }

    leaf message-period {
      type performance-monitoring-interval-type;
      default 100;

      description 
        "This object specifies the interval between Delay Measurement OAM
         message transmission. For Delay Measurement monitoring applications,
         the default value is 100ms.";
    }

    leaf priority {
      type cfm:priority-type;
      mandatory true;

      description 
        "This object specifies the priority of frames with Performance
         Monitoring OAM message information.";
    }

    leaf frame-size {
      type uint32 {
        range "64 .. 9600";
      }
      default 64;

      description 
        "This object specifies the Delay Measurement frame size between 64 bytes
         and the maximum transmission unit of the EVC.

         The range of frame sizes from 64 through 2000 octets need to be
         supported, and the range of frame sizes from 2001 through 9600
         octets is suggested to be supported.
                 
         The adjustment to the frame size of the standard frame size is
         accomplished by the addition of a Data or Test TLV. A Data or
         Test TLV is only added to the frame if the frame size is
         greater than 64 bytes.";
    }

    leaf data-pattern {
      type enumeration {
        enum zeroes {
          description "Indicates the Data TLV contains all zeros.";
        }
        enum ones {
          description "Indicates the Data TLV contains all ones.";
        }
      }
      default zeroes;

      description 
        "This object specifies the DM data pattern included in a Data TLV when
         the size of the DM frame is determined by the frame-size object
         and test-tlv-included is 'false'.  If the frame size object
         does not define the DM frame size or test-tlv-included is
         'true' the value of this object is ignored.";
    }

    leaf test-tlv-included {
      type boolean;
      default false;

      description 
        "Indicates whether a Test TLV or Data TLV is included when the size of
         the LBM frame is determined by the frame-size leaf.
                 
         A value of 'true' indicates that the Test TLV is to be
         included.
                 
         A value of 'false' indicates that the Data TLV is to be
         included.";
      reference
        "[Y.1731] 9.3";
    }

    leaf test-tlv-pattern {
      type test-pattern-type;
      default null-signal-without-crc-32;

      description 
        "This object specifies the type of test pattern to be sent in the DM
         frame Test TLV when the size of DM PDU is determined by the
         frame-size object and test-tlv-included is 'true'. If the frame
         size object does not define the DM frame size or
         test-tlv-included is 'false' the value of this object can be
         ignored.";
    }

    leaf measurement-interval {
      type uint32 {
        range "1..1440";
      }
      units minutes;
      default 15;

      description 
        "This object specifies a Measurement Interval in minutes.
                 
         A Measurement Interval 15 minutes needs to be supported, other
         intervals may be supported.";
      reference
        "MEF-SOAM-PM-MIB.mefSoamDmCfgMeasurementInterval";
    }

    leaf number-intervals-stored {
      type uint32 {
        range "2..1000";
      }
      default 32;

      description 
        "This object specifies the number of completed measurement intervals to
         store in the history statistic table.
                 
         At least 32 completed measurement intervals are to be
         stored. 96 measurement intervals are recommended to be stored.";
    }

    leaf align-measurement-intervals {
      type boolean;
      default true;

      description 
        "This object specifies whether the Measurement Intervals for the Delay
         Measurement session are aligned with a zero offset to real
         time.
                 
         The value 'true' indicates that each Measurement Interval
         starts at a time which is aligned to NE time source hour, if
         the repetition time (or the Measurement Interval, if the
         repetition time is 0) is a factor of an hour, i.e. 60min/15min
         = 4. For instance, a Measurement Interval/Repetition Time of 15
         minutes would stop/start the Measurement Interval at 0, 15, 30,
         and 45 minutes of an hour. A Measurement Interval/Repetition
         Time of 7 minutes would not align to the hour since 7 minutes
         is NOT a factor of an hour, i.e.  60min/7min = 8.6.  In this
         case the behavior is the same as if the object is set to
         'false'.
                 
         The value 'false' indicates that the first Measurement Interval
         starts at an arbitrary time and each subsequent Measurement
         Interval starts at a time which is determined by
         repetition-time.";
    }

    leaf align-measurement-offset {
      type uint32 {
        range "0..525600";
      }
      units minutes;
      default 0;

      description 
        "This object specifies the offset in minutes from the time of day value
         if align-measurement-intervals is 'true' and the repetition
         time is a factor of 60 minutes. If not, the value of this
         object is ignored.
                 
         If the Measurement Interval is 15 minutes and
         align-measurement-intervals is true and if this object was set
         to 5 minutes, the Measurement Intervals would start at 5, 20,
         35, 50 minutes past each hour.";
    }

    leaf bins-per-fd-interval {
      type uint32 {
        range "2..100";
      }
      default 3;

      description 
        "This object specifies the number of measurement bins per Measurement
         Interval for Frame Delay measurements.
                 
         At least 3 bins are to be supported; at least 10 bins are
         recommended to be supported.";
    }

    leaf bins-per-ifdv-interval {
      type uint32 {
        range "2..100";
      }
      default 2;

      description 
        "This object specifies the number of measurement bins per Measurement
         Interval for Inter-Frame Delay Variation measurements.
                 
         The minimum number of measurement bins to be supported is
         2. The desired number of measurements bins to be supported is
         10.";
    }

    leaf ifdv-selection-offset {
      type yang:gauge32 {
        range "1..100";
      }
      default 1;

      description 
        "This object specifies the selection offset for Inter-Frame Delay
         Variation measurements.  If this value is set to n, then the
         IFDV is calculated by taking the difference in frame delay
         between frame F and frame (F+n).";
      reference
        "MEF-SOAM-PM-MIB.mefSoamDmCfgInterFrameDelayVariationSelectionOffset";
    }

    leaf bins-per-fdr-interval {
      type uint32;
      default 2;

      description
        "This object specifies the number of measurement bins per Measurement
         Interval for Frame Delay Range measurements.";
      reference
        "[MEF SOAM PM IA] R31, D15, R32, D16
         MEF-SOAM-PM-MIB.mefSoamDmCfgNumMeasBinsPerFrameDelayRangeInterval";
    }

    leaf session-type {
      type enumeration {
        enum proactive {
          description
            "The current session is 'proactive'";
        }
        enum on-demand {
          description
            "The current session is 'on-demand'";
        }
      }
      mandatory true;

      description
        "This object indicates whether the current session is defined to be
         'proactive' or 'on-demand'.";
      reference
        "[MEF SOAM IA] R3";
    }
        
    list thresholds {
      key id;
      description 
        "This list contains the Delay Measurement threshold configuration values
         for DM Performance Monitoring.
                 
         The main purpose of the threshold configuration list is to
         configure threshold alarm notifications indicating that a
         specific performance metric is not being met.";

      leaf id {
        type uint32 {
          range "1..2147483647";
        }

        description 
          "The index of the threshold number for the specific DM threshold
           entry.
                     
           An index value of '1' is to be supported. Other index values
           can be supported.";
      }

      leaf enabled-thresholds {
        type bits {
          bit measured-frame-delay-two-way;
          bit max-frame-delay-two-way;
          bit average-frame-delay-two-way;
          bit measured-inter-frame-delay-variation-two-way;
          bit max-inter-frame-delay-variation-two-way;
          bit average-inter-frame-delay-variation-two-way;
          bit max-frame-delay-range-two-way;
          bit average-frame-delay-range-two-way;
          bit measured-frame-delay-forward;
          bit max-frame-delay-forward;
          bit average-frame-delay-forward;
          bit measured-inter-frame-delay-variation-forward;
          bit max-inter-frame-delay-variation-forward;
          bit average-inter-frame-delay-variation-forward;
          bit max-frame-delay-range-forward;
          bit average-frame-delay-range-forward;
          bit measured-frame-delay-backward;
          bit max-frame-delay-backward;
          bit average-frame-delay-backward;
          bit measured-inter-frame-delay-variation-backward;
          bit max-inter-frame-delay-variation-backward;
          bit average-inter-frame-delay-variation-backward;
          bit max-frame-delay-range-backward;
          bit average-frame-delay-range-backward;
        }
        default " ";

        description 
          "A vector of bits that indicates the type of SOAM DM threshold
           notifications that are enabled.
                     
           A present bit enables the specific SOAM DM threshold
           notification and when the specific counter is enabled and the
           threshold is crossed a notification is generated.
                     
           A not present bit disables the specific SOAM DM threshold
           notification.
                     
           If a particular SOAM DM threshold is not supported the BIT
           value is not present.";
        reference
          "MEF-SOAM-PM-MIB.mefSoamDmThresholdCfgEnable";
      }

      leaf measured-frame-delay-two-way {
        type yang:gauge32;
        units microseconds;
        default 2147483647;

        description 
          "This object is used to set the measurement two-way delay threshold
           value that will be used to determine if a threshold
           notification is generated.";
        reference
          "MEF-SOAM-PM-MIB." +
          "mefSoamDmThresholdCfgMeasuredFrameDelayTwoWayThreshold";
      }

      leaf max-frame-delay-two-way {
        type yang:gauge32;
        units microseconds;
        default 2147483647;

        description 
          "This object is used to set the maximum two-way delay threshold value
           that will be used to determine if a threshold notification is
           generated.";
        reference
          "MEF-SOAM-PM-MIB.mefSoamDmThresholdCfgMaxFrameDelayTwoWayThreshold";
      }

      leaf average-frame-delay-two-way {
        type yang:gauge32;
        units microseconds;
        default 2147483647;

        description 
          "This object is used to set the average two-way delay threshold value
           that will be used to determine if a threshold notification is
           generated.";
        reference
          "MEF-SOAM-PM-MIB.mefSoamDmThresholdCfgAvgFrameDelayTwoWayThreshold";
      }

      leaf measured-inter-frame-delay-variation-two-way {
        type yang:gauge32;
        units microseconds;
        default 2147483647;

        description 
          "This object is used to set the measurement two-way IFDV threshold
           value that will be used to determine if a threshold notification is
           generated.";
        reference
          "MEF-SOAM-PM-MIB.mefSoamDmThresholdCfgMeasuredIfdvTwoWayThreshold";
      }

      leaf max-inter-frame-delay-variation-two-way {
        type yang:gauge32;
        units microseconds;
        default 2147483647;

        description 
          "This object is used to set the maximum two-way IFDV threshold value
           that will be used to determine if a threshold notification is
           generated.";
        reference
          "MEF-SOAM-PM-MIB.mefSoamDmThresholdCfgMaxIfdvTwoWayThreshold";
      }

      leaf average-inter-frame-delay-variation-two-way {
        type yang:gauge32;
        units microseconds;
        default 2147483647;

        description 
          "This object is used to set the average two-way IFDV threshold value
           that will be used to determine if a threshold notification is
           generated.";
        reference
          "MEF-SOAM-PM-MIB.mefSoamDmThresholdCfgAvgIfdvTwoWayThreshold";
      }
      leaf max-frame-delay-range-two-way {
        type yang:gauge32;
        units microseconds;
        default 2147483647;

        description 
          "This object is used to set the maximum two-way Frame Delay Range
           threshold value that will be used to determine if a threshold
           notification is generated.";
        reference
          "MEF-SOAM-PM-MIB." +
          "mefSoamDmThresholdCfgMaxFrameDelayRangeTwoWayThreshold";
      }
      leaf average-frame-delay-range-two-way {
        type yang:gauge32;
        units microseconds;
        default 2147483647;

        description 
          "This object is used to set the average two-way Frame Delay Range
           threshold value that will be used to determine if a threshold
           notification is generated.";
        reference
          "MEF-SOAM-PM-MIB." +
          "mefSoamDmThresholdCfgAvgFrameDelayRangeTwoWayThreshold";
      }
      leaf measured-frame-delay-forward {
        type yang:gauge32;
        units microseconds;
        default 2147483647;

        description 
          "This object is used to set the measurement forward delay thresh-old
           value that will be used to determine if a threshold
           notification is generated.";
        reference
          "MEF-SOAM-PM-MIB." +
          "mefSoamDmThresholdCfgMeasuredFrameDelayForwardThreshold";
      }

      leaf max-frame-delay-forward {
        type yang:gauge32;
        units microseconds;
        default 2147483647;

        description 
          "This object is used to set the maximum forward delay threshold value
           that will be used to determine if a threshold notification is
           generated.";
        reference
          "MEF-SOAM-PM-MIB." +
          "mefSoamDmThresholdCfgMaxFrameDelayForwardThreshold";
      }

      leaf average-frame-delay-forward {
        type yang:gauge32;
        units microseconds;
        default 2147483647;

        description 
          "This object is used to set the average forward delay threshold value
           that will be used to determine if a threshold notification is
           generated.";
        reference
          "MEF-SOAM-PM-MIB.mefSoamDmThresholdCfgAvgFrameDelayForwardThreshold";
      }

      leaf measured-inter-frame-delay-variation-forward {
        type yang:gauge32;
        units microseconds;
        default 2147483647;

        description 
          "This object is used to set the measurement IFDV threshold value that
           will be used to determine if a threshold notification is
           generated.";
        reference
          "MEF-SOAM-PM-MIB.mefSoamDmThresholdCfgMeasuredIfdvForwardThreshold";
      }

      leaf max-inter-frame-delay-variation-forward {
        type yang:gauge32;
        units microseconds;
        default 2147483647;

        description 
          "This object is used to set the maximum IFDV threshold value that will
           be used to determine if a threshold notification is generated.";
        reference
          "MEF-SOAM-PM-MIB.mefSoamDmThresholdCfgMaxIfdvForwardThreshold";
      }

      leaf average-inter-frame-delay-variation-forward {
        type yang:gauge32;
        units microseconds;
        default 2147483647;

        description 
          "This object is used to set the average IFDV threshold value that will
           be used to determine if a threshold notification is generated.";
        reference
          "MEF-SOAM-PM-MIB.mefSoamDmThresholdCfgAvgIfdvForwardThreshold";
      }

      leaf max-frame-delay-range-forward {
        type yang:gauge32;
        units microseconds;
        default 2147483647;

        description 
          "This object is used to set the maximum Frame Delay Range threshold
           value that will be used to determine if a threshold
           notification is generated.";
        reference
          "MEF-SOAM-PM-MIB." +
          "mefSoamDmThresholdCfgMaxFrameDelayRangeForwardThreshold";
      }

      leaf average-frame-delay-range-forward {
        type yang:gauge32;
        units microseconds;
        default 2147483647;

        description 
          "This object is used to set the average Frame Delay Range threshold
           value that will be used to determine if a threshold
           notification is generated.";
        reference
          "MEF-SOAM-PM-MIB." +
          "mefSoamDmThresholdCfgAvgFrameDelayRangeForwardThreshold";
      }

      leaf measured-frame-delay-backward {
        type yang:gauge32;
        units microseconds;
        default 2147483647;

        description 
          "This object is used to set the measurement backward delay threshold
           value that will be used to determine if a threshold
           notification is generated.";
        reference
          "MEF-SOAM-PM-MIB." +
          "mefSoamDmThresholdCfgMeasuredFrameDelayBackwardThreshold";
      }

      leaf max-frame-delay-backward {
        type yang:gauge32;
        units microseconds;
        default 2147483647;

        description 
          "This object is used to set the maximum backward delay threshold value
           that will be used to determine if a threshold notification is
           generated.";
        reference
          "MEF-SOAM-PM-MIB.mefSoamDmThresholdCfgMaxFrameDelayBackwardThreshold";
      }

      leaf average-frame-delay-backward {
        type yang:gauge32;
        units microseconds;
        default 2147483647;

        description 
          "This object is used to set the average backward delay threshold value
           that will be used to determine if a threshold notification is
           generated.";
        reference
          "MEF-SOAM-PM-MIB.mefSoamDmThresholdCfgAvgFrameDelayBackwardThreshold";
      }

      leaf measured-inter-frame-delay-variation-backward {
        type yang:gauge32;
        units microseconds;
        default 2147483647;

        description 
          "This object is used to set the measurement backward IFDV thresh-old
           value that will be used to determine if a threshold
           notification is generated.";
        reference
          "MEF-SOAM-PM-MIB.mefSoamDmThresholdCfgMeasuredIfdvBackwardThreshold";
      }

      leaf max-inter-frame-delay-variation-backward {
        type yang:gauge32;
        units microseconds;
        default 2147483647;
        description 
          "This object is used to set the maximum backward IFDV threshold value
           that will be used to determine if a threshold notification is
           generated.";
        reference
          "MEF-SOAM-PM-MIB.mefSoamDmThresholdCfgMaxIfdvBackwardThreshold";
      }

      leaf average-inter-frame-delay-variation-backward {
        type yang:gauge32;
        units microseconds;
        default 2147483647;
        description 
          "This object is used to set the average backward IFDV threshold value
           that will be used to determine if a threshold notification
           is generated.";
        reference
          "MEF-SOAM-PM-MIB.mefSoamDmThresholdCfgAvgIfdvBackwardThreshold";
      }
      leaf max-frame-delay-range-backward {
        type yang:gauge32;
        units microseconds;
        default 2147483647;

        description 
          "This object is used to set the maximum backward Frame Delay Range
           threshold value that will be used to determine if a threshold
           notification is generated.";
        reference
          "MEF-SOAM-PM-MIB." +
          "mefSoamDmThresholdCfgMaxFrameDelayRangeBackwardThreshold";
      }

      leaf average-frame-delay-range-backward {
        type yang:gauge32;
        units microseconds;
        default 2147483647;

        description 
          "This object is used to set the average backward Frame Delay Range
           threshold value that will be used to determine if a threshold
           notification is generated.";
        reference
          "MEF-SOAM-PM-MIB." +
          "mefSoamDmThresholdCfgAvgFrameDelayRangeBackwardThreshold";
      }
    }
  }

  grouping delay-measurement-stats-group {
    description
      "This grouping includes statistics objects for a SOAM Delay Measurement
       session.";

    leaf suspect-status {
      type suspect-status-type;
      description 
        "Whether the Measurement Interval has been marked as suspect.
                 
         The object is to be set to false at the start of a measurement
         interval. It is set to true when there is a discontinuity in
         the performance measurements during the Measurement Interval.
         Conditions for a discontinuity include, but are not limited to
         the following:
                 
          1 - The local time-of-day clock is adjusted by at least 10 seconds
          2 - The conducting of a performance measurement is halted before the
              current Measurement Interval is completed
          3 - A local test, failure, or reconfiguration that disrupts service";
    }

    leaf frame-delay-two-way-min {
      type yang:gauge32;
      units microseconds;

      description 
        "This object contains the minimum two-way frame delay calculated by this
         MEP for this Measurement Interval.
                 
         This object is undefined if measurement-type is dm1-transmitted
         or dm1-received.";
    }

    leaf frame-delay-two-way-max {
      type yang:gauge32;
      units microseconds;

      description 
        "This object contains the maximum two-way frame delay calculated by this
         MEP for this Measurement Interval.
                 
         This object is undefined if measurement-type is dm1DmTx or
         dm1-received.";
    }

    leaf frame-delay-two-way-average {
      type yang:gauge32;
      units microseconds;

      description 
        "This object contains the average two-way frame delay calculated by this
         MEP for this Measurement Interval.
                 
         This object is undefined if measurement-type is dm1-transmitted or
         dm1-received.";
    }
    leaf frame-delay-forward-min {
      type yang:gauge32;
      units microseconds;

      description 
        "This object contains the minimum one-way frame delay in the forward
        direction calculated by this MEP for this Measurement
        Interval. The value of this object may not be accurate in the
        absence of sufficiently precise clock synchronization.
                 
        This object is undefined if measurement-type is dm1-transmitted.";
    }

    leaf frame-delay-forward-max {
      type yang:gauge32;
      units microseconds;

      description 
        "This object contains the maximum one-way frame delay in the forward
         direction calculated by this MEP for this Measurement
         Interval. The value of this object may not be accurate in the
         absence of sufficiently precise clock synchronization.
                 
         This object is undefined if measurement-type is dm1-transmitted.";
    }

    leaf frame-delay-forward-average {
      type yang:gauge32;
      units microseconds;

      description 
        "This object contains the average one-way frame delay in the forward
         direction calculated by this MEP for this Measurement
         Interval. The value of this object may not be accurate in the
         absence of sufficiently precise clock synchronization.
                 
         This object is undefined if measurement-type is dm1-transmitted.";
    }

    leaf frame-delay-backward-min {
      type yang:gauge32;
      units microseconds;

      description 
        "This object contains the minimum one-way frame delay in the backward
         direction calculated by this MEP for this Measurement
         Interval. The value of this object may not be accurate in the
         absence of sufficiently precise clock synchronization.
                 
         This object is undefined if measurement-type is dm1-transmitted
         or dm1-received.";
    }

    leaf frame-delay-backward-max {
      type yang:gauge32;
      units microseconds;

      description 
        "This object contains the maximum one-way frame delay in the backward
         direction calculated by this MEP for this Measurement
         Interval. The value of this object may not be accurate in the
         absence of sufficiently precise clock synchronization.
                 
         This object is undefined if measurement-type is dm1-transmitted or
         dm1-received.";
    }

    leaf frame-delay-backward-average {
      type yang:gauge32;
      units microseconds;

      description 
        "This object contains the average one-way frame delay in the backward
         direction calculated by this MEP for this Measurement
         Interval. The value of this object may not be accurate in the
         absence of sufficiently precise clock synchronization.
                 
         This object is undefined if measurement-type is dm1-transmitted or
         dm1-received.";
    }

    leaf inter-frame-delay-variation-forward-min {
      type yang:gauge32;
      units microseconds;
      description 
        "This object contains the minimum one-way inter-frame delay interval in
         the forward direction calculated by this MEP for this
         Measurement Interval.
                 
         The value of this object is undefined when measurement-type is
         dm1-transmitted.";
    }

    leaf inter-frame-delay-variation-forward-max {
      type yang:gauge32;
      units microseconds;

      description 
        "This object contains the maximum one-way inter-frame delay interval in
         the forward direction calculated by this MEP for this
         Measurement Interval.
                 
         The value of this object is undefined when measurement-type is
         dm1-transmitted.";
    }

    leaf inter-frame-delay-variation-forward-average {
      type yang:gauge32;
      units microseconds;

      description 
        "This object contains the average one-way inter-frame delay interval in
         the forward direction calculated by this MEP for this
         Measurement Interval.

         The value of this object is undefined when measurement-type is
         dm1-transmitted.";
    }

    leaf inter-frame-delay-variation-backward-min {
      type yang:gauge32;
      units microseconds;

      description 
        "This object contains the minimum one-way inter-frame delay interval in
         the backward direction calculated by this MEP for this
         Measurement Interval.
                 
        The value of this object is undefined when measurement-type is
        dm1-transmitted or dm1-received.";
    }

    leaf inter-frame-delay-variation-backward-max {
      type yang:gauge32;
      units microseconds;

      description 
        "This object contains the maximum one-way inter-frame delay interval in
         the backward direction calculated by this MEP for this
         Measurement Interval.
                 
         The value of this object is undefined when measurement-type is
         dm1-transmitted or dm1-received.";
    }

    leaf inter-frame-delay-variation-backward-average {
      type yang:gauge32;
      units microseconds;

      description 
        "This object contains the average one-way inter-frame delay interval in
         the backward direction calculated by this MEP for this
         Measurement Interval.
                 
         The value of this object is undefined when measurement-type is
         dm1-transmitted or dm1-received.";
    }

    leaf inter-frame-delay-variation-two-way-min {
      type yang:gauge32;
      units microseconds;

      description 
        "This object contains the minimum two-way inter-frame delay interval
         calculated by this MEP for this Measurement Interval.
                 
         The value of this object is undefined when measurement-type is
         dm1-transmitted or dm1-received.";
    }

    leaf inter-frame-delay-variation-two-way-max {
      type yang:gauge32;
      units microseconds;

      description 
        "This object contains the maximum two-way inter-frame delay interval
         calculated by this MEP for this Measurement Interval.
                 
         The value of this object is undefined when measurement-type is
         dm1-transmitted or dm1-received.";
    }

    leaf inter-frame-delay-variation-two-way-average {
      type yang:gauge32;
      units microseconds;

      description 
        "This object contains the average two-way inter-frame delay interval
         calculated by this MEP for this Measurement Interval.
                 
         The value of this object is undefined when measurement-type is
         dm1-transmitted or dm1-received.";
    }

    leaf frame-delay-range-forward-max {
      type yang:gauge32;
      units microseconds;

      description 
        "This object contains the maximum one-way Frame Delay Range in the
         forward direction calculated by this MEP for this Measurement
         Interval.
                 
         The value of this object is undefined when measurement-type is
         dm1-transmitted.";
    }

    leaf frame-delay-range-forward-average {
      type yang:gauge32;
      units microseconds;

      description 
        "This object contains the average one-way Frame Delay Range in the
         forward direction calculated by this MEP for this Measurement
         Interval.
                 
         The value of this object is undefined when measurement-type is
         dm1-transmitted.";
    }

    leaf frame-delay-range-backward-max {
      type yang:gauge32;
      units microseconds;

      description 
        "This object contains the maximum one-way Frame Delay Range in the
         backward direction calculated by this MEP for this Measurement
         Interval.
                 
         The value of this object is undefined when measurement-type is
         dm1-transmitted or dm1-received.";
    }

    leaf frame-delay-range-backward-average {
      type yang:gauge32;
      units microseconds;

      description 
        "This object contains the average one-way Frame Delay Range in the
         backward direction calculated by this MEP for this Measurement
         Interval.
                 
         The value of this object is undefined when measurement-type is
         dm1-transmitted or dm1-received.";
    }

    leaf frame-delay-range-two-way-max {
      type yang:gauge32;
      units microseconds;

      description 
        "This object contains the maximum two-way Frame Delay Range calculated
         by this MEP for this Measurement Interval.
                 
         The value of this object is undefined when measurement-type is
         dm1-transmitted or dm1-received.";
    }

    leaf frame-delay-range-two-way-average {
      type yang:gauge32;
      units microseconds;

      description 
        "This object contains the average two-way Frame Delay Range calculated
         by this MEP for this Measurement Interval.
                 
         The value of this object is undefined when measurement-type is
         dm1-transmitted or dm1-received.";
    }
    leaf soam-pdus-sent {
      type yang:gauge32;

      description 
        "This object contains the count of the number of SOAM PDUs sent during
         this Measurement Interval.
                 
         This object applies when measurement-type is dmm or
         dm1-transmitted and is undefined if measurement-type is
         dm1-received. It indicates the number of DMM or 1DM SOAM frames
         transmitted.";
    }

    leaf soam-pdus-received {
      type yang:gauge32;
      description 
        "This object contains the count of the number of SOAM PDUs received in
         this Measurement Interval.
                 
         This object indicates the number of DMR and 1DM SOAM frames
         received. This object applies when measurement-type is dmm or
         dm1-received and is undefined if measurement-type is
         dm1-transmitted.";
    }
  }

  grouping delay-measurement-bins-content-group {
    description
      "This grouping contains result measurement bin objects for a SOAM Delay
       Measurement session.";

    leaf type {
      type measurement-bin-type;

      description
        "This object specifies whether the bin number is for Frame De-lay,
         Inter-Frame Delay Variation or Frame Delay Range.";
    }

    leaf number {
      type uint32;

      description 
        "This object specifies the bin number for the configured boundary.  The
         first bin has bin number 1.";
    }

    leaf lower-bound {
      type yang:gauge32;
      units microseconds;

      description 
        "This object specifies the lower boundary for a measurement bin. The
         upper boundary is defined by the next bin value or infinite for
         the last bin defined.  The measurement boundary for each
         measurement bin is to be larger than the measurement boundary
         of the preceding measurement bin. By default, the next bin is
         set to 5000us larger than the lower bin boundary.

         The values in a bin boundary object represents the time range
         used to segregate delay data into the appropriate statistical
         data bin. For five bins with default values, each bin has the
         following time range:
                 
          bin 1 =     0, range is 0us
          bin 2 =  5000, range is 5,000us
          bin 3 = 10000, range is 10,000us
          bin 4 = 15000, range is 15,000us
          bin 5 = 20000, range is 20,000us 

        The first bin boundary (number set to 1) always contains the
        value of 0. Attempting to write a non-zero value to this bin
        will result in an error.";
    }

    leaf counter {
      type yang:gauge32;
      config false;

      description 
        "This object contains the count of the number of completed measurements
         initiated in this Measurement Interval whose value falls within
         the range specified for this bin (that is, greater than or
         equal to the measurement boundary for the bin, and (unless the
         bin is the last bin) less than the measurement boundary for the
         following bin.";
      reference
        "MEF-SOAM-PM-MIB.mefSoamDmCurrentStatsBinsCounter";
    }
  }

  grouping delay-measurement-bins-group {
    description
      "This grouping contains the top-level structure for the three types of
       measurements (frame delay, inter frame delay variation, and frame
       delay range)";

    container bins {
      description
        "This container defines the bins content for FD, IFDR, and FDR
         sessions.";
      
      list frame-delay {
        key "type number";
        uses delay-measurement-bins-content-group;

        description
          "Data definitions related to frame delay bins content.";
      }

      list inter-frame-delay-variation {
        key "type number";
        uses delay-measurement-bins-content-group;

        description
          "Data definitions related to inter frame delay bins content.";
      }

      list frame-delay-range {
        key "type number";
        uses delay-measurement-bins-content-group;

        description
          "Data definitions related to frame delay range bins content.";
      }
    }
  }

  //
  // Augments into CFM related to MEF SOAM PM
  //

  augment "/cfm:maintenance-domain/cfm:maintenance-association" +
          "/cfm:maintenance-association-end-point" {
    description
      "This set of data definitions extends the MEG End Point (as described in
       Y.1731) or Maintenance End Point (as described in 802.1q) defined
       in the MEF CFM module (MEF-CFM), specifically with regards to the
       role of the MEP in PM tests.";

    leaf loss-single-ended-responder {
      type boolean;
      default true;

      description 
        "This object specifies whether the Loss Measurement (LMM) single-ended
         Responder is enabled.
                 
         The value 'true' indicates the single-ended Loss Measurement
         Responder is enabled and if a LMM message is received a LMR
         will be sent in re-ply.
                 
         The value 'false' indicates the single-ended Loss Measurement
         Responder is disabled. If a LMM message is received no
         response will be sent and the message will be discarded.
                 
         This object needs to be persistent upon reboot or restart of a
         device.
                 
         A MEP can be both a single-ended Responder and Controller
         simultaneously.";
      reference
        "MEF-SOAM-PM-MIB.mefSoamPmMepLmSingleEndedResponder";
    }

    leaf synthetic-loss-single-ended-responder {
      type boolean;
      default true;

      description 
        "This object specifies whether the Synthetic Loss Measurement (SLM)
         single-ended Responder is enabled.
                 
         The value 'true' indicates the single-ended SLM Responder is
         enabled and if a SLM message is received a SLR will be sent in
         reply.
                 
         The value 'false' indicates the single-ended SLM Responder is
         disabled.  If a SLM message is received no response
         will be sent and the message will be discarded.
                 
         This object needs to be persistent upon reboot or restart of a
         device.
                 
         A MEP can be both a single-ended Responder and Controller
         simultaneously.";
      reference
        "MEF-SOAM-PM-MIB.mefSoamPmMepSlmSingleEndedResponsder";
    }

    leaf delay-single-ended-responder {
      type boolean;
      default true;

      description 
        "This object specifies whether the Delay Measurement (DMM) single ended
         Responder is enabled.
                 
         The value 'true' indicates the single-ended Delay Measurement
         Responder is enabled and if a DMM message is received a DMR
         will be sent in re-ply.
                 
         The value 'false' indicates the single-ended Delay Measurement
         Responder is disabled. If a DMM message is received no
         response will be sent and the message will be discarded.
                 
         This object needs to be persistent upon reboot or restart of a
         device.
                 
         A MEP can be both a single-ended Responder and Controller
         simultaneously.";
      reference
        "MEF-SOAM-PM-MIB.mefSoamPmMepDmSingleEndedResponder";
    }
  }

  augment "/cfm:maintenance-domain/cfm:maintenance-association" +
          "/cfm:maintenance-association-end-point" {
    description
      "This set of data definitions extends the MEG End Point (as described
       Y.1731) or Maintenance End Point (as described in 802.1q) defined
       in the MEF CFM module (MEF-CFM), specifically with regards to
       Loss Measurement.";

    container loss-measurements {
      description
        "This container contains a collection of data definitions re-lated to
         Loss Measurements.";

      list loss-measurement {
        key session-id;
        config false;
        description
          "A list of Loss Measurement PM Sessions where each in-stance is uniquely
           identified by an id attribute.";

        leaf session-id {
          type uint32;

          description 
            "This object uniquely identifies a scheduled measurement. It is
             automatically generated by the server on creation of a new
             measurement.";
        }

        leaf session-status {
          type session-status-type;
          config false;

          description 
            "This object indicates the current status of the LM session. A value
             of 'active' indicates the current LM session is active,
             i.e. the current time lies between the start time and the
             stop time, and enabled is true. A value of 'not-active'
             indicates the current LM session is not active, i.e. it has
             not started yet, has stopped upon reaching the stop time,
             or is disabled.";
        }

        uses loss-measurement-configuration-group;
        uses remote-mep-group;
        uses measurement-timing-group;

        leaf measured-forward-flr {
          type yang:gauge32 {
            range "0..100000";
          }
          units milli-percent;

          description 
            "This object contains the Frame Loss Ratio in the forward direction
             calculated by this MEP from the last received SOAM PDU. The
             FLR value is a ratio that is expressed as a percent with a
             value of 0 (ratio 0.00) through 100000 (ratio 1.00).
                         
             Units are in milli-percent, where 1 indicates 0.001
             per-cent.";
          reference
            "MEF-SOAM-PM-MIB.mefSoamLmMeasuredStatsForwardFlr";
        }

        leaf measured-backward-flr {
          type yang:gauge32 {
            range "0..100000";
          }
          units milli-percent;

          description 
            "This object contains the Frame Loss Ratio in the backward direction
             calculated by this MEP from the last received SOAM PDU. The
             FLR value is a ratio that is expressed as a percent with a
             value of 0 (ratio 0.00) through 100000 (ratio 1.00).
                         
             Units are in milli-percent, where 1 indicates 0.001
             percent.";
          reference
            "MEF-SOAM-PM-MIB.mefSoamLmMeasuredStatsBackwardFlr";
        }

        leaf measured-availability-forward-status {
          type availability-type;

          description 
            "This object indicates the availability status (the outcome of the
             last availability indicator) in the forward direction based upon
             the last received SOAM PDU.";
          reference
            "MEF-SOAM-PM-MIB.mefSoamLmMeasuredStatsAvailForwardStatus";
        }

        leaf measured-availability-backward-status {
          type availability-type;

          description 
            "This object indicates the availability status (the outcome of the
             last availability indicator) in the backward direction based
             upon the last received SOAM PDU.";
          reference
            "MEF-SOAM-PM-MIB.mefSoamLmMeasuredStatsAvailBackwardStatus";
        }

        leaf measured-forward-last-transition-time {
          type yang:date-and-time;
          description 
            "This object indicates the time of the last transition between
             available and unavailable in the forward direction.
                         
             If there have been no transitions since the Loss
             Measurement Session was started, this is set to 0.";
          reference
            "MEF-SOAM-PM-MIB." +
            "mefSoamLmMeasuredStatsAvailForwardLastTransitionTime";
        }

        leaf measured-backward-last-transition-time {
          type yang:date-and-time;
          description 
            "This object indicates the time of the last transition between
             available and unavailable in the backward direction.
                         
             If there have been no transitions since the Loss Measurement
             Session was started, this is set to 0.";
          reference
            "MEF-SOAM-PM-MIB." +
            "mefSoamLmMeasuredStatsAvailBackwardLastTransitionTime";
        }
        container current-availability-stats {
          description 
            "This container contains the current results for a SOAM Loss
             Measurement session for availability statistics gathered during the
             interval indicated by availability-measurement-interval.";

          leaf id {
            type uint32;
            description 
              "The index for the current availability Measurement Interval for
               this PM session. This value will become the value for id of the
               history-availability-stats list once the Measurement
               Interval is completed.  The duration of the Measurement
               Interval is specified by availability-measurement-interval.";
          }

          leaf start-time {
            type yang:date-and-time;
            mandatory true;

            description
              "The time that the current Measurement Interval started.";
          }

          leaf elapsed-time {
            type uint32 {
              range "0..2147483647";
            }
            mandatory true;

            description 
              "The time that the current Measurement Interval has been running,
               in 0.01 seconds.";
          }

          uses loss-availability-stats-group;
        }

        container current-measurement-stats {
          description 
            "This container contains the results for the current Measurement
             Interval in a SOAM Loss Measurement session gathered during
             the interval indicated by measurement-interval.";

          leaf id {
            type uint32;

            description 
              "The index for the current Measurement Interval for this PM
               session. This value will become the value for id of the
               history-measurement-stats list once the Measurement
               Interval is completed.";
          }

          leaf start-time {
            type yang:date-and-time;
            mandatory true;

            description
              "The time that the current Measurement Interval started.";
          }

          leaf elapsed-time {
            type uint32 {
              range "0..2147483647";
            }
            mandatory true;

            description 
              "The time that the current Measurement Interval has been running,
               in 0.01 seconds.";
          }

          uses loss-measurement-stats-group;
        }

        list history-availability-stats {
          key id;
          description 
            "This list contains the results for availability history Measurement
             Intervals in a SOAM Loss Measurement session.";

          leaf id {
            type uint32;
            description 
              "The index for the availability Measurement Interval within this
               PM session.";
          }

          leaf end-time {
            type yang:date-and-time;
            mandatory true;

            description
              "The time that the Measurement Interval ended.";
          }

          leaf elapsed-time {
            type uint32 {
              range "0..2147483647";
            }
            mandatory true;

            description 
              "The length of time that the Measurement Interval ran for,
               in 0.01 seconds.";
          }

          uses loss-availability-stats-group;
        }

        list history-measurement-stats {
          key id;
          description 
            "This list contains the results for history Measurement
             Intervals in a SOAM Loss Measurement session.";

          leaf id {
            type uint32;

            description 
              "The index for the Measurement Interval within this
               PM session.";
          }

          leaf end-time {
            type yang:date-and-time;
            mandatory true;

            description
              "The time that the Measurement Interval ended.";
          }

          leaf elapsed-time {
            type uint32 {
              range "0..2147483647";
            }
            mandatory true;

            description 
              "The length of time that the Measurement Interval ran for,
              in 0.01 seconds.";
          }

          uses loss-measurement-stats-group;
        }
      }
    }
  }

  augment "/cfm:maintenance-domain/cfm:maintenance-association" +
          "/cfm:maintenance-association-end-point" {
    description
      "This set of data definitions extends the MEG End Point (as described in
           Y.1731) or Maintenance End Point (as described in 802.1q)
           defined in the MEF CFM module (MEF-CFM), specifically with
           regards to Delay Measurement.";

    container delay-measurements {
      description
        "This container contains a collection of data definitions related to
         Delay Measurements.";

      list delay-measurement {
        key id;
        config false;
        description
          "A list of Delay Measurement PM Sessions where each instance is
           uniquely identified by an id attribute.";

        leaf id {
          type string;
 
          description 
            "This object uniquely identifies a scheduled measurement. It is
             automatically generated by the server on creation of a new
             measurement.";
        }

        leaf session-status {
          type session-status-type;
          config false;

          description 
            "This object indicates the current status of the DM session. A value
             of 'active' indicates the current DM session is active,
             i.e. the current time lies between the start time and the
             stop time, and enabled is true. A value of 'not-active'
             indicates the current DM session is not active, i.e. it has
             not started yet, has stopped upon reaching the stop time,
             or is disabled.";
        }

        uses delay-measurement-configuration-group;
        uses remote-mep-group;
        uses measurement-timing-group;

        leaf source-mac-address {
          type yang:mac-address;

          description 
            "The Source MAC Address Field of the received SOAM DM session PDUs.
                         
             If measurement-type is dm1-received this object indicates
             the source address of the dm1-transmitted DM session.
                         
             This object is only valid for measurement-type set to
             dm1-received. It is ignored for measurement-type set to dmm
             or dm1-transmitted.";
        }

        leaf frame-delay-two-way {
          type yang:gauge32;
          units microseconds;
          description 
            "This object contains the two-way frame delay calculated by this MEP
             from the last received SOAM PDU.
                         
             This object is undefined is measurement-type is
             dm1-transmitted or dm1-received.";
          reference
            "MEF-SOAM-PM-MIB.mefSoamDmMeasuredStatsFrameDelayTwoWay";
        }

        leaf frame-delay-forward {
          type yang:gauge32;
          units microseconds;
          description 
            "This object contains the frame delay in the forward direction
             calculated by this MEP from the last received SOAM PDU. The value
             of this object may not be accurate in the absence of
             sufficiently precise clock synchronization.
                         
             This object is undefined is measurement-type is
             dm1-transmitted.";
          reference
            "MEF-SOAM-PM-MIB.mefSoamDmMeasuredStatsFrameDelayForward";
        }

        leaf frame-delay-backward {
          type yang:gauge32;
          units microseconds;

          description 
            "This object contains the frame delay in the backward direction
             calculated by this MEP from the last received SOAM PDU. The
             value of this object may not be accurate in the absence of
             sufficiently precise clock synchronization.

             This object is undefined is measurement-type is
             dm1-transmitted or dm1-received.";
          reference
            "MEF-SOAM-PM-MIB.mefSoamDmMeasuredStatsFrameDelayBackward";
        }

        leaf inter-frame-delay-variation-two-way {
          type yang:gauge32;
          units microseconds;

          description 
            "This object contains the last two-way inter-frame delay interval
             calculated by this MEP.
                         
             The value of this object is undefined when measurement-type
             is dm1-transmitted or dm1-received.";
          reference
            "MEF-SOAM-PM-MIB.mefSoamDmMeasuredStatsIfdvTwoWay";
        }

        leaf inter-frame-delay-variation-forward {
          type yang:gauge32;
          units microseconds;

          description 
            "This object contains the last one-way inter-frame delay interval in
             the forward direction calculated by this MEP.
                         
             The value of this object is undefined when measurement-type
             is dm1-transmitted.";
          reference
            "MEF-SOAM-PM-MIB.mefSoamDmMeasuredStatsIfdvForward";
        }

        leaf inter-frame-delay-variation-backward {
          type yang:gauge32;
          units microseconds;

          description 
            "This object contains the last one-way inter-frame delay interval in
             the backward direction calculated by this MEP.
                         
             The value of this object is undefined when measurement-type
             is dm1-transmitted or dm1-received.";
          reference
            "MEF-SOAM-PM-MIB.mefSoamDmMeasuredStatsIfdvBackward";
        }

        container current-stats {
          description 
            "This container contains the results for the current Measurement
             Interval in a SOAM Delay Measurement session gathered
             during the interval indicated by measurement-interval.";
 
         leaf start-time {
            type yang:date-and-time;
            mandatory true;

            description
              "The time that the current Measurement Interval started.";
          }

          leaf elapsed-time {
            type uint32 {
              range "0..2147483647";
            }
            mandatory true;

            description 
              "The time that the current Measurement Interval has been running,
               in 0.01 seconds.";
          }

          uses delay-measurement-stats-group;
          uses delay-measurement-bins-group;
        }

        list history-stats {
          key id;
          description 
            "This list contains the results for history Measurement Intervals in
             a SOAM Delay Measurement session.";

          leaf id {
            type uint32;
 
            description 
              "The identifier for the Measurement Interval within this
               PM session.";
          }

          leaf end-time {
            type yang:date-and-time;
            mandatory true;

            description
              "The time that the Measurement Interval ended.";
          }

          leaf elapsed-time {
            type uint32 {
              range "0..2147483647";
            }
            mandatory true;

            description 
              "The length of time that the Measurement Interval ran for, in 0.01
               seconds.";
          }

          uses delay-measurement-stats-group;
          uses delay-measurement-bins-group;
        }
      }
    }
  }

  //
  // RPCs related to MEF SOAM PM
  //

  rpc create-loss-measurement {
    description 
      "Schedule a one-way and two-way on-demand and proactive performance
       monitoring loss measurements on a specific MEP.

       A list entry associated with the newly created session will be
       created in the loss-measurements container and the assigned
       session identifier will be returned in the output parameter.";

    input {
      uses loss-measurement-configuration-group;
      uses remote-mep-group;
      uses measurement-timing-group;
    }

    output {
      leaf session-id {
        type uint32;
        mandatory true;

        description
          "The session identifier of the newly created loss measurement
           session.";
      }
    }
  }

  rpc abort-loss-measurement {
    description 
      "Abort a currently running or scheduled single-ended on-demand ETH-LM
       function. This operation is not applicable to dual-ended
       proactive ETH-LM.";

    input {
      leaf maintenance-domain-id {
        type string;

        description
          "The ID of a Maintenance Domain of the MEP on which the measurement
           session should be aborted";
      }

      leaf maintenance-association-id {
        type string;

        description
          "The ID of a Maintenance Association of the MEP on which the measurement
           session should be aborted";
      }


      leaf mep-id {
        type cfm:mep-id-type;
        mandatory true;
            
        description
          "The ID of the MEP on which a measurement session should be aborted";
      }

      leaf session-id {
        type uint32;
        mandatory true;

        description
          "The session ID of the measurement session to be aborted.";
      }
    }
  }

  rpc clear-loss-history-stats {
    description 
      "Clear the Loss Measurement history list (history-availability-stats and
       history-measurement-stats) for a specific session. All instance
       data is deleted.";

    input {
      leaf maintenance-domain-id {
        type string;

        description
          "The ID of a Maintenance Domain of the MEP on which the loss
           measurement history should be cleared";
      }

      leaf maintenance-association-id {
        type string;

        description
          "The ID of a Maintenance Association of the MEP on which the loss
           measurement history should be cleared";
      }

      leaf mep-id {
        type cfm:mep-id-type;
        mandatory true;

        description
          "The ID of the MEP on which the loss measurement history should be
           cleared.";
      }

      leaf session-id {
        type uint32;
        mandatory true;

        description
          "The session ID of the loss measurement session of which the loss
           measurement history should be cleared";
      }
    }
  }

  rpc create-delay-measurement {
    description 
      "Schedule one-way and two-way on-demand and proactive performance
       monitoring frame delay measurements on a specific MEP.

       A list entry associated with the newly created session will be
       created in the delay-measurements container and the assigned
       session identifier will be returned in the output parameter.";

    input {
      uses delay-measurement-configuration-group;
      uses remote-mep-group;
      uses measurement-timing-group;
    }

    output {
      leaf session-id {
        type uint32;
        mandatory true;

        description
          "The session identifier of the newly created delay measurement
           session.";
      }
    }
  }

  rpc abort-delay-measurement {
    description 
      "Abort a pre-scheduled instances of performance monitoring";

    input {
      leaf maintenance-domain-id {
        type string;

        description
          "The ID of a Maintenance Domain of the MEP on which a measurement
           session should be aborted";
      }

      leaf maintenance-association-id {
        type string;

        description
          "The ID of a Maintenance Association of the MEP on which a measurement
           session should be aborted";
      }
      leaf mep-id {
        type cfm:mep-id-type;
        mandatory true;
          
        description
          "The ID of the MEP on which a measurement session should be aborted";
      }

      leaf session-id {
        type uint32;
        mandatory true;
          
        description
          "The session ID of the measurement session to be aborted.";
      }
    }
  }

  rpc clear-delay-history-stats {
    description 
      "Clear the Delay Measurement history list (history-stats) for a specific
       session. All instance data is deleted.";

    input {
      leaf maintenance-domain-id {
        type string;

        description
          "The ID of a Maintenance Domain of the MEP on which the loss
           measurement history should be cleared";
      }

      leaf maintenance-association-id {
        type string;

        description
          "The ID of a Maintenance Association of the MEP on which the
           loss measurement history should be cleared";
      }
      leaf mep-id {
        type cfm:mep-id-type;
        mandatory true;
          
        description
          "The ID of the MEP on which the loss measurement history should be
           cleared.";
      }

      leaf session-id {
        type uint32;
        mandatory true;

        description
          "The session ID of the loss measurement session of which the loss
           measurement history should be cleared";
      }
    }
  }

  //
  // Notifications related to MEF SOAM PM
  //

  notification availability-change-alarm {
    description 
      "An availability-change-alarm notification is sent when the state of
       measured-availability-forward-status or
       measured-availability-backward-status associated with a specific
       loss-measurement session changes.";
    reference
      "MEF-SOAM-PM-MIB.mefSoamAvailabilityChangeAlarm";

    leaf maintenance-domain-id {
      type string;

      description
        "The ID of a Maintenance Domain of the MEP on which the availability
         change alarm is present";
    }

    leaf maintenance-association-id {
      type string;

      description
        "The ID of a Maintenance Association of the MEP on which the availability
         change alarm is present";
    }

    leaf mep-id {
      type cfm:mep-id-type;
      mandatory true;
          
      description
        "A reference to the specific MEP on which the availability change alarm
         is present";
    }

    leaf session-id {
      type uint32;
      mandatory true;

      description
        "A reference to the loss-measurement session in which the availability
         change alarm occurred.";
    }

    leaf measured-availability-forward-status {
      type availability-type;

      description 
        "The current value of measured-availability-forward-status of the
         referenced loss-measurement session.";
    }

    leaf measured-availability-backward-status {
      type availability-type;

      description 
        "The current value of measured-availability-backward-status of the
         referenced loss-measurement session.";
    }

    leaf measured-forward-last-transition-time {
      type yang:date-and-time;

      description 
        "The current value of measured-forward-last-transition-time of the
         referenced loss-measurement session.";
    }

    leaf measured-backward-last-transition-time {
      type yang:date-and-time;

      description 
        "The current value of measured-backward-last-transition-time of the
         referenced loss-measurement session.";
    }

    leaf forward-available {
      type yang:gauge32;

      description 
        "The current value of forward-available of the referenced
         loss-measurement session.";
    }

    leaf backward-available {
      type yang:gauge32;

      description 
        "The current value of backward-available of the referenced
         loss-measurement session.";
    }

    leaf forward-unavailable {
      type yang:gauge32;

      description 
        "The current value of forward-unavailable of the referenced
         loss-measurement session.";
    }

    leaf backward-unavailable {
      type yang:gauge32;

      description 
        "The current value of backward-unavailable of the referenced
         loss-measurement session.";
    }
  }

  notification loss-session-start-stop-alarm {
    description 
      "A loss-session-start-stop-alarm notification is sent when the state of
       session-status changes for a specific loss-measurement session.";
    reference
      "MEF-SOAM-PM-MIB.mefSoamLmSessionStartStopAlarm";

    leaf maintenance-domain-id {
      type string;

      description
        "The ID of a Maintenance Domain of the MEP on which the loss session
         state change alarm is present";
    }

    leaf maintenance-association-id {
      type string;

      description
        "The ID of a Maintenance Association of the MEP on which the loss
         session state change alarm is present";
    }

    leaf mep-id {
      type cfm:mep-id-type;
      mandatory true;

      description
        "A reference to the specific MEP on which the loss session state
         change alarm occurred.";
    }

    leaf session-id {
      type uint32;
      mandatory true;
          
      description
        "A reference to the loss-measurement session in which the loss session
         state change alarm occurred.";
    }
        
    leaf session-status {
      type session-status-type;

      description 
        "The current value of session-status of the referenced loss-measurement
         session.";
    }
  }

  notification delay-session-start-stop-alarm {
    description 
      "A delay-session-start-stop-alarm notification is sent when the state of
       session-status changes for a specific delay-measurement session.";
    reference
      "MEF-SOAM-PM-MIB.mefSoamDmSessionStartStopAlarm";

    leaf maintenance-domain-id {
      type string;

      description
        "The ID of a Maintenance Domain of the MEP on which the delay
         session state change alarm is present";
    }

    leaf maintenance-association-id {
      type string;

      description
        "The ID of a Maintenance Association of the MEP on which the delay
         session state change alarm is present";
    }

    leaf mep-id {
      type cfm:mep-id-type;
      mandatory true;

      description
        "A reference to the specific MEP on which the delay session state
         change alarm occurred.";
    }

    leaf session-id {
      type uint32;
      mandatory true;
          
      description
        "A reference to the delay-measurement session in which the delay session
         state change alarm occurred.";
    }

    leaf session-status {
      type session-status-type;
      description 
        "The current value of session-status of the referenced delay-measurement
         session.";
    }
  }

  notification threshold-crossing-alarm {
    description 
      "A threshold-crossing-alarm notification is sent if the following
       conditions are met for a particular type.
             
       For an above-alarm five conditions need to be met:
        - measurement of the parameter is enabled via enabled-thresholds
          for a LM or a DM crossing; and
        - the parameter threshold is configured in the thresholds list
          for an LM or DM session.
        - the threshold crossing type of threshold-above-alarm is
          enabled in alarm-enable; and
        - the measured value of the parameter exceeds the value
          configured in the thresholds list for an LM or DM crossing
          entry for a type of threshold-above-alarm.
        - no previous threshold-crossing-alarm notifications with type
          above-alarm have been sent relating to the same threshold and
          the same parameter, during this measurement interval.
             
       For a set-alarm five conditions need to be met:
        - measurement of the parameter is enabled via measurement-enable
          for a LM or a DM crossing; and
        - the parameter threshold is configured in the thresholds list
          for an LM or DM session.
        - the threshold crossing type of threshold-set-clear-alarm is
          enabled in alarm-enable; and
        - the measured value of the parameter exceeds the value
          configured in the thresholds list for an LM or DM crossing
          entry for a type of threshold-set-clear-alarm.
        - no previous threshold-crossing-alarm notifications with type
          threshold-set-clear have been sent relating to the same
          threshold and the same parameter, during this measurement
          interval.

        For a clear-alarm five conditions need to be met:
         - measurement of the parameter is enabled via enabled-thresholds
           for a LM or a DM crossing; and
         - the parameter threshold is configured in the thresholds list
           for an LM or DM session.
         - the threshold crossing type of threshold-set-clear-alarm is
           enabled in alarm-enable; and
         - no previous threshold-crossing-alarm notifications with type
           threshold-set-clear have been sent relating to the same
           threshold and the same parameter, during this measurement
           interval.
             
        In the case of thresholds applied to a maximum or average
        measurement counter, the previous measured value is the value of
        the counter at the end of the preceding measurement interval.
        In the case of thresholds applied to the last measured value, it
        is the previous measured value.
             
        An agent is not to generate more than one
        threshold-crossing-alarm of a given type per LM or DM session as
        specified by alarm-interval. A 'notification-event' is the
        transmission of a single notification to a list of notification
        destinations.
             
        If additional threshold crossing events occur within the
        alarm-interval period, then notification generation for these
        changes are suppressed by the agent until the current alarm
        interval expires. At the end of an alarm interval period, one
        notification-event is generated if any threshold crossing events
        occurred since the start of the alarm interval period.  In such
        a case, another alarm interval period is started right away.";
    reference
      "MEF-SOAM-PM-MIB.mefSoamPmThresholdCrossingAlarm";


    leaf maintenance-domain-id {
      type string;

      description
        "The ID of a Maintenance Domain of the MEP on which the threshold
         crossing alarm occurred";
    }

    leaf maintenance-association-id {
      type string;

      description
        "The ID of a Maintenance Association of the MEP on which the threshold
         crossing alarm occurred";
    }
    leaf mep-id {
      type cfm:mep-id-type;
      mandatory true;

      description
        "A reference to the specific MEP on which the threshold crossing alarm
         occurred.";
    }

    container measurement-id {
      description
        "This container describes the measurement ID for a loss or delay
         measurement.";

      choice measurement-id {
        mandatory true;
        description
          "The measurement ID can reference either a loss or a delay measurement
           session.";

        leaf loss-measurement-session-id {
          type uint32;

          description 
            "The session identifier for the loss-measurement session affected by
             the notification.";
        }

        leaf delay-measurement-session-id {
          type uint32;

          description 
            "The session identifier for the delay-measurement session affected
             by the notification.";
        }
      }
    }

    leaf notification-crossing-type {
      type enumeration {
        enum above-alarm {
          description
            "Indicates that the crossing type alarm was an above threshold.";
        }
        enum set-alarm {
          description
            "Indicates that the crossing type alarm was a set threshold.";
        }
        enum clear-alarm {
          description
            "Indicates that the crossing type alarm was a clear threshold.";
        }
      }
      description
        "This object indicates the crossing type that caused the generation of
         the notification.";
      reference
        "MEF-SOAM-PM-MIB.mefSoamPmNotificationObjCrossingType";
    }

    leaf threshold-id {
      type enumeration {
        enum measured-flr-forward {
          description
            "Indicates the measured Frame Loss Ratio forward threshold generated
             the notification.";
        }
        enum max-flr-forward {
          description
            "Indicates the maximum Frame Loss Ration forward threshold generated
             the notification.";
        }
        enum average-flr-forward {
          description
            "Indicates the average Frame Loss Ratio forward threshold generated
             the notification.";
        }
        enum measured-flr-backward {
          description
            "Indicates the measured Frame Loss Ratio backward threshold
             generated the notification.";
        }
        enum max-flr-backward {
          description
            "Indicates the maximum Frame Loss Ratio backward threshold generated
             the notification.";
        }
        enum forward-high-loss {
          description
            "Indicates the forward High Loss threshold generated the
             notification.";
        }
        enum forward-consecutive-high-loss {
          description
            "Indicates the forward Consecutive High Loss threshold generated the
             notification.";
        }
        enum backward-high-loss {
          description
            "Indicates the backward High Loss threshold generated the
             notification.";
        }
        enum backward-consecutive-high-loss {
          description
            "Indicates the backward Consective High Loss threshold generated the
             notification.";
        }
        enum forward-unavailable-count {
          description
            "Indicates the forward Unavailable count threshold generated the
             notification.";
        }
        enum forward-available-ratio {
          description
            "Indicates the forward Available ration threshold generated the
             notification.";
        }
        enum backward-unavailable-count {
          description
            "Indicates the backward Unavailable count threshold generated the
             notification.";
        }
        enum backward-available-ratio {
          description
            "Indicates the backward Available ratio threshold generated the
             notification.";
        }
        enum measured-frame-delay-two-way {
          description
            "Indicates the measured Frame Delay two-way threshold generated
             the notification.";
        }
        enum max-frame-delay-two-way {
          description
            "Indicates the maximum Frame Delay two-way threshold generated the
             notification.";
        }
        enum average-frame-delay-two-way {
          description
            "Indicates the average Frame Delay two-way threshold generated the
             notification.";
        }
        enum measured-inter-frame-delay-variation-two-way {
          description
            "Indicates the measured IFDV two-way threshold generated the
             notification.";
        }
        enum max-inter-frame-delay-variation-two-way {
          description
            "Indicates the maximum IFDV two-way threshold generated the
             notification.";
        }
        enum average-inter-frame-delay-variation-two-way {
          description
            "Indicates the average IFDV two-way threshold generat-ed the
             notification.";
        }
        enum max-frame-delay-range-two-way {
          description
            "Indicates the maximum Frame Delay Range two-way threshold generated
             the notification.";
        }
        enum average-frame-delay-range-two-way {
          description
            "Indicates the average Frame Delay Range two-way threshold generated
             the notification.";
        }
        enum measured-frame-delay-forward {
          description
            "Indicates the measured Frame Delay forward threshold generated the
             notification.";
        }
        enum max-frame-delay-forward {
          description
            "Indicates the maximum Frame Delay forward threshold generated the
             notification.";
        }
        enum average-frame-delay-forward {
          description
            "Indicates the average Frame Delay forward threshold generated the
             notification.";
        }
        enum measured-inter-frame-delay-variation-forward {
          description
            "Indicates the measured IFDV forward threshold generated the
             notification.";
        }
        enum max-inter-frame-delay-variation-forward {
          description
            "Indicates the maximum IFDV forward threshold generated the
             notification.";
        }
        enum average-inter-frame-delay-variation-forward {
          description
            "Indicates the average IFDV forward threshold generated the
             notification.";
        }
        enum max-frame-delay-range-forward {
          description
            "Indicates the maximum Frame Delay Range forward threshold generated
             the notification.";
        }
        enum average-frame-delay-range-forward {
          description
            "Indicates the average Frame Delay Range forward threshold generated
             the notification.";
        }
        enum measured-frame-delay-backward {
          description
            "Indicates the measured Frame Delay backward threshold generated the
             notification.";
        }
        enum max-frame-delay-backward {
          description
            "Indicates the maximum Frame Delay backward threshold generated the
             notification.";
        }
        enum average-frame-delay-backward-threshold {
          description
            "Indicates the average Frame Delay backward threshold generated the
             notification.";
        }
        enum measured-inter-frame-delay-variation-backward {
          description 
            "Indicates the measured IFDV backward threshold gener-ated the
             notification.";
        }
        enum max-inter-frame-delay-variation-backward {
          description
            "Indicates the maximum IFDV backward threshold gener-ated the
             notification.";
        }
        enum average-inter-frame-delay-variation-backward {
          description
            "Indicates the average IFDV backward threshold gener-ated the
             notification.";
        }
        enum max-frame-delay-range-backward {
          description
            "Indicates the maximum Frame Delay Range backward threshold
             generated the notification.";
        }
        enum average-frame-delay-range-backward {
          description
            "Indicates the average Frame Delay Range backward threshold
             generated the notification.";
        }
      }

      description
        "This object identifies the threshold that caused the generation of the
         notification.";
      reference
        "MEF-SOAM-PM-MIB.mefSoamPmNotificationObjThresholdId";
    }

    leaf threshold-config-value {
      type uint32;

      description 
        "The configured threshold value of the object that caused the generation
         of the notification.";
      reference
        "MEF-SOAM-PM-MIB.mefSoamPmNotificationObjThresholdConfig";
    }

    leaf measured-value {
      type uint32;

      description 
        "The measured value of the object at the time of the generation of the
         notification.";
      reference
        "MEF-SOAM-PM-MIB.mefSoamPmNotificationObjThresholdValue";
    }

    leaf suspect {
      type suspect-status-type;

      description 
        "The suspect flag for the current measurement interval in which the
         notification was generated.";
      reference
        "MEF-SOAM-PM-MIB.mefSoamPmNotificationObjSuspect";
    }
  }
}
